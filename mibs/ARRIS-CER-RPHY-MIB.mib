ARRIS-CER-RPHY-MIB DEFINITIONS ::= BEGIN

IMPORTS
    X509Certificate
        FROM DOCS-BPI2-MIB
    arrisE6Cer
        FROM ARRIS-MIB
    InterfaceIndex, 
    InterfaceIndexOrZero
        FROM IF-MIB
    FirmwareSource, 
    InetAddressIPv4or6, 
    AdminState,
    PrimaryState,
    SecondaryState,
    DsVidGrpName
        FROM CADANT-TC
    NodeName
        FROM CLAB-TOPO-MIB
    TenthdBmV, TenthdB
        FROM DOCS-IF-MIB
    PhysicalIndex
        FROM ENTITY-MIB
    InetAddressType,
    InetAddress,
    InetPortNumber
        FROM INET-ADDRESS-MIB
    IANAifType
        FROM IANAifType-MIB
    Counter32,
    Counter64,
    Gauge32,
    TimeTicks,
    Unsigned32,
    Integer32,
    OBJECT-TYPE,
    MODULE-IDENTITY,
    NOTIFICATION-TYPE
        FROM SNMPv2-SMI
    TruthValue,
    MacAddress,
    TEXTUAL-CONVENTION, 
    RowStatus, 
    DisplayString,
    DateAndTime,
    PhysAddress,
    TimeStamp
        FROM SNMPv2-TC
    OBJECT-GROUP
        FROM SNMPv2-CONF
    SnmpAdminString
        FROM SNMP-FRAMEWORK-MIB
    trapCounter,
    trapSeverity
        FROM CADANT-CMTS-EQUIPMENT-MIB
    cadIfCmtsModIndex,
    cadIfUsOfdmaTmpltIndex,
    CadOfdmaDataTemplateIndexType
        FROM CADANT-CMTS-UPCHANNEL-MIB
    ifIndex
        FROM IF-MIB;
        
cerRphyMib MODULE-IDENTITY
    LAST-UPDATED "202204290000Z" -- 29 April 2022
    ORGANIZATION
        "Arris International"
    CONTACT-INFO
        "Network Management
         Postal: Arris International.
         4343 Commerce Court
         Lisle, IL 60532
         Tel: +1 630 281 3000
         Email: support@arris.com"
    DESCRIPTION
        "This MIB contains objects for RPHY configuration and status on the ARRIS E6000 CER."

    REVISION "202204290000Z" -- 29 April 2022
    DESCRIPTION
        "Add cerRpdDsRfPortMeasuredPower to the CerRpdDsRfPortEntry."
    REVISION "202106070000Z" -- 7 June 2021
    DESCRIPTION
        "Rename cerRpdUsBasePowerTable to cerRpdUsRfPortTable.
         Add cerRpdUsRfPortSfLevel" 
    REVISION "202104140000Z" -- 14 April 2021
    DESCRIPTION
        "Add cerRphyIpAddrType."                 
    REVISION "202103310000Z" -- 31 March 2021
    DESCRIPTION
        "Remove cerRpdNameHighCinLatency.  
         Change SYNTAX of cerRpdNameCinLatency to Unsigned32 (0..20000)"
    REVISION "202101220000Z" -- 22 Jan 2021
    DESCRIPTION
        "Add ethernet source port for static PWs"
    REVISION "202012180000Z" -- 18 Dec 2020
    DESCRIPTION
        "Fix high range of rpd exclusion zones."
    REVISION "202011180000Z" -- 18 November 2020
    DESCRIPTION
        "Change default value of cerRphyL2TPv3ConnectionSetupTimeout to 90"  
    REVISION "202010080000Z" -- 8 October 2020
    DESCRIPTION
        "Add cerRpdAuxCoreTable"      
    REVISION "202009180000Z" -- 18 Sep 2020
    DESCRIPTION
        "Add RMD configuration file management entries to cerRphyGroup"
    REVISION "202008250000Z" -- 25 August 2020
    DESCRIPTION
        "Add initialConfigRetriesExceeded(9) to cerRpdAuxCoreStatusFailureType"  
    REVISION "202007300000Z" -- 30 July 2020
    DESCRIPTION
        "Remove 80 KHz from cerOobNdrUsChanWidth"  
    REVISION "202007270000Z" -- 27 July 2020
    DESCRIPTION
        "Change cerOobNdfDsChanDataPwId and cerOobNdrUsChanDataPwId to read-write. 
         Change cerDsGrpToPwMcastAddrPwMcastIpAddr to read-create."
    REVISION "202007140000Z" -- 14 July 2020
    DESCRIPTION
        "Change the following MIB objects back to read_write:
         cerOobNdfDsChanCenterFreq, cerOobNdfDsChanWidth, cerOobNdfDsChanPowerAdj,
         cerOobNdrUsChanCenterFreq, cerOobNdrUsChanWidth and cerOobNdrUsChanPowerTgt"
    REVISION "202007060000Z" -- 6 July 2020
    DESCRIPTION
        "Change the following MIB objects to read_only:
         cerOobNdfDsChanDataPwId, cerOobNdfDsChanCenterFreq,
         cerOobNdfDsChanWidth, cerOobNdfDsChanPowerAdj,
         cerOobNdrUsChanDataPwId, cerOobNdrUsChanCenterFreq,
         cerOobNdrUsChanWidth and cerOobNdrUsChanPowerTgt"
    REVISION "202007020000Z" -- 2 July 2020
    DESCRIPTION
        "Change cerOobNdrUsChanSrcIpAddrType and cerOobNdrUsChanSrcIpAddr to read_only"
    REVISION "202006240000Z" -- 24 Jun 2020
    DESCRIPTION
        "Add cerRphyUnknownRpd notification/trap as well as its objects"
    REVISION "202003090000Z" -- 9 Mar 2020
    DESCRIPTION
        "Add cerOobNdrUsChanSrcIpAddrType, cerOobNdrUsChanSrcIpAddr"
    REVISION "202002210000Z" -- 21 Feb 2020
    DESCRIPTION
        "Add cerRphyDlmMode, cerRpdNameHighCinLatency, and cerRphySessionInfoChanType"
    REVISION "201909250000Z" -- 25 Sep 2019
    DESCRIPTION
        "Remove the following MIB tables: 
         cerOob551OmTable, cerOob551DsChanTable, cerOob551NcTable
         cerOob551VArpdTable, cerOob551VirtUsRfPortTable, cerOob551VirtUsChanTable
         cerOobRpdToArpdTable"
    REVISION "201909180000Z" -- 18 Sep 2019
    DESCRIPTION
        "Change range of cerOobNdrUsChanPowerTgt to -100..100"
    REVISION "201909170000Z" -- 17 Sep 2019
    DESCRIPTION
        "Change SYNTAX and UNITS of cerOobNdrUsChanPowerTgt to TenthdB"
    REVISION "201909150000Z" -- 15 Sep 2019
    DESCRIPTION
        "Add support for tracking rpd ethernet ports and gcp on a tunnel basis.
         Remove cerRphyBcAddrToChanTable
         Change range of cerRpdDsRfPortTilt to 160
         Remove cerRphyCwToneRfPortId from cerRphyCwToneEntry."
    REVISION "201909050000Z" -- 5 Sep 2019
    DESCRIPTION
        "Change default value of cerRpdUsBasePowerLevel to -60"
    REVISION "201908190000Z" -- 19 Aug 2019
    DESCRIPTION
        "Change default values on cerRpdDataPnmCapabSupportedPnmTests and
         cerRpdDataPnmCapabUpcSupportsFreqDomainSamples"
    REVISION "201908150000Z" -- 15 Aug 2019
    DESCRIPTION
        "Remove cerRpdIpAddrTable"
    REVISION "201908070000Z" -- 7 Aug 2019
    DESCRIPTION
        "Add cerRphyTargetPowerAdjTable"
    REVISION "201908060000Z" -- 6 Aug 2019
    DESCRIPTION
        "Add cerRpdDataPnmCapabSupportedPnmTests, cerRpdDataPnmCapabUtscNumSacs
		 cerRpdDataPnmCapabUpcMinNumSymbols25Khz, cerRpdDataPnmCapabUpcMaxNumSymbols25Khz
		 cerRpdDataPnmCapabUpcMinNumSymbols50Khz, cerRpdDataPnmCapabUpcMaxNumSymbols50Khz
		 cerRpdDataPnmCapabUpcSupportsStaggeredPies, cerRpdDatadPnmCapabUpcSupportsDedicatedPwUpcRxMer
		 and cerRpdDataPnmCapabUpcSupportsFreqDomainSamples to CerRpdDataEntry"
    REVISION "201907290000Z" -- 29 July 2019
    DESCRIPTION
        "Add DEFVAL for cerRpdUsScQamPreambleResponseTimestamp and
         cerRpdUsOfdmaPreambleResponseTimestamp"
    REVISION "201907240000Z" -- 24 July 2019
    DESCRIPTION
        "Update to v.06 US Preamble Interop and V0.4 CORE Software PSAs"
    REVISION "201906250000Z" -- 25 June 2019
    DESCRIPTION
        "Update to v0.3 CORE Software R9.0"
    REVISION "201906130000Z" -- 13 June 2019
    DESCRIPTION
        "Update to v1.4 RPHY Ring/Daisy Chain Configurations"
    REVISION "201906070000Z" -- 7 June 2019
    DESCRIPTION
        "Added cerRphyUsScQamConfigPreambleTable, cerRphyUsScQamModPreambleTable,
         cerRpdUsOfdmaTmpltPreambleTable and cerRpdUsOfdmaConfigPreambleTable"
    REVISION "201905290000Z" -- 29 May 2019
    DESCRIPTION
        "Update cerRpdNameAdpHdTimeout range to 60..120 and defval to 60"
    REVISION "201905060000Z" -- 6 May 2019
    DESCRIPTION
        "Added video and broadcast to cerRphyDscpPktType"
    REVISION "201904120000Z" -- 12 April 2019
    DESCRIPTION
        "Update to v2.2 NDF draft PSA"
    REVISION "201904020000Z" -- 2 April 2019
    DESCRIPTION
        "Changed cerOobNdfDsChanCenterFreq, cerOobNdrUsChanCenterFreq, cerOobNdfDsChanDataPwId, cerOobNdrUsChanDataPwId defval to 0"
    REVISION "201902260000Z" -- 26 February 2019
    DESCRIPTION
        "Changed cerOobNdrUsChanDataPwId from read-only to read-write."
    REVISION "201901220000Z" -- 22 January 2019
    DESCRIPTION
        "Changed the SYNTAX/type for cerRpdEnetDiagsTemp from Unsigned32 to Integer32"
    REVISION "201901200000Z" -- 20 January 2019
    DESCRIPTION
        "Update to v1.1 NDF PSA"
    REVISION "201901150000Z" -- 15 January 2019
    DESCRIPTION
        "Add the cerRpdEnetDiagsTable MIB table"
    REVISION "201901140000Z" -- 14 January 2019
    DESCRIPTION
        "Update cerRpdUsExclLowFreq and cerRpdUsExclHighFreq range to 5-204. Allow 0 for cerOobNdfDsChanDataPwId"
    REVISION "201901090000Z" -- 9 January 2019
    DESCRIPTION
        "Update to v0.1 CORE OFDMA PSA"
    REVISION "201812190000Z" -- 19 December 2018        
    DESCRIPTION
        "Update to v0.5 RPHY Ring/Daisy Chain Configurations"
    REVISION "201811130000Z" -- 13 November 2018
    DESCRIPTION
        "Add cerRphyMcastBackupInterface, cerRphyMcastActiveInterface and cerRphyMcastRevertToPrimaryInterface"
    REVISION "201811080000Z" -- 8 November 2018
    DESCRIPTION
        "Update to v3.3 CORE PSA"
    REVISION "201809250000Z" -- 25 September 2018
    DESCRIPTION
        "Update to v0.3 NDF PSA"
    REVISION "201809170000Z" -- 17 September 2018
    DESCRIPTION
        "Remove cerRpdDataUpTime from cerRpdDataTable.
         Add cerRpdIfRfPortId to cerRpdIfTable.
         Add cerRpdDsStatsRpdIndex, cerRpdDsStatsRfPortId to cerRpdDsChanStatsTable."
    REVISION "201808010000Z" -- 1 August 2018
    DESCRIPTION
        "Update to v2.3 CCAP PSA"
    REVISION "201807100000Z" -- 10 July 2018
    DESCRIPTION
        "Update to v2.2 Security PSA and v2.2 CCAP PSA"
    REVISION "201805250000Z" -- 25 May 2018
    DESCRIPTION
        "Update to v2.2 Security PSA and v1.7 CCAP PSA"
    REVISION "201803280000Z" -- 28 March 2018
    DESCRIPTION
        "Update to v2.2 Security PSA and v.09 CCAP PSA"
    REVISION "201710110000Z" -- 11 October 2017
    DESCRIPTION
        "Update to v.05 CCAP PSA and v2.1 Security PSA"
    REVISION "201601290800Z" -- 29 January 2016
    DESCRIPTION
        "E6000 CER Initial revision."
    ::= {arrisE6Cer 9}

CerRpdName ::= TEXTUAL-CONVENTION
    STATUS    current
    DESCRIPTION
        "The name of an RPD. Zero length string means not set."
    SYNTAX    OCTET STRING (SIZE(0..16))

CerRpdIndex ::= TEXTUAL-CONVENTION
    STATUS    current
    DESCRIPTION
        "The global index of an RPD."
    SYNTAX Unsigned32 (1..511)

CerRpdIndexOrZero ::= TEXTUAL-CONVENTION
    STATUS    current
    DESCRIPTION
        "The global index of an RPD. Zero means not all RPDs."
    SYNTAX Unsigned32 (0..511)

PwOperState ::= TEXTUAL-CONVENTION
    STATUS current
    DESCRIPTION
        "Indicates the operational status of the PW.
          - up(1): Ready to pass packets.
          - down(2): PW signaling is not yet finished, or
                     indications available at the service
                     level indicate that the PW is not
                     passing packets.
          - testing(3): AdminStatus at the PW level is set to
                        test.
          - dormant(4): The PW is not in a condition to pass
                        packets but is in a 'pending' state,
                        waiting for some external event.
          - notPresent(5): Some component is missing to accomplish
                           the setup of the PW. It can be
                           configuration error, incomplete
                           configuration, or a missing H/W component.
          - lowerLayerDown(6): One or more of the lower-layer interfaces
                               responsible for running the underlying PSN
                               Is not in OperStatus 'up' state."
    SYNTAX INTEGER {
        up(1),
        down(2),
        testing(3),
        dormant(4),
        notPresent(5),
        lowerLayerDown(6)
    }

PwStatus ::= TEXTUAL-CONVENTION
    STATUS current
    DESCRIPTION
        "Indicates the status of the PW and the interfaces affecting
        this PW. If none of the bits are set, it indicates no faults
        are reported."
    SYNTAX BITS {
        pwNotForwarding(0),
        servicePwRxFault(1),
        servicePwTxFault(2),
        psnPwRxFault(3),
        psnPwTxFault(4)
    }

PwErrorCode ::= TEXTUAL-CONVENTION
    STATUS current
    DESCRIPTION
        "Indicates the PW error code when the PW oper State is down.
        'invalidMACInterfaceValue'  
           Indicates wrong assignment of the M-CMTS MAC interface
           ifIndex.
        'invalidDSInterfaceValue'  
           Indicates wrong assignment of the M-CMTS Downstream 
           interface ifIndex.
        'noResourcesForDSInterfaceIfIndex' 
           Indicates the M-CMTS Core has no more resources to
           assign a session to this entry.
        'l2tpv3Error'
           An L2TPv3 StopCCN or CDN message was issued.
        'ifAdminStatusSetToDown'
           Indicates the ifAdminStatus was set to down and the
           session was torn down. More details are in the Row 
           Status and ifAdminStatus relationship, described in 
           docsIfMCmtsDepiSessionConfigRowStatus."
    SYNTAX INTEGER  {
        none(1),
        invalidMACInterfaceValue(2),
        invalidDSInterfaceValue(3),
        noResourcesForDSInterfaceIndex(4),
        l2tpv3Error(5),
        ifAdminStatusSetToDown(6)
    }

PwType ::= TEXTUAL-CONVENTION
    STATUS current
    DESCRIPTION
        "Indicates the type of DEPI Pseudowire (Session):
             Psp-Packet Streaming Protocol
             Mpt-MPEG-TS mode of DEPI"
    SYNTAX INTEGER {
        psp(0),
        mpt(1)
    }

PwSubtype ::= TEXTUAL-CONVENTION
    STATUS current
    DESCRIPTION
        "Indicates the subtype of DEPI Pseudowire (Session):"
    SYNTAX INTEGER {
        mptLegacy(0),
        mptDepi(1),             -- MPEG packets, both video and 55-1 FWD
        pspLegacy(2),
        mcm(3),
        pspDepiMultichannel(4),
        reserved(5),
        pspUepiScQam(6),
        pspUepiOfdma(7),
        pspBwReqScQam(8),
        pspBwReqOfdma(9),
        pspProbe(10),
        pspRngReqScQam(11),
        pspRngReqOfdma(12),
        pspMapScQam(13),
        pspMapOfdma(14),
        pspSpecman(15),
        pspPnm(16),
        psp551Fwd(17),
        psp551Ret(18),
        psp552Fwd(19),
        psp552Ret(20),
        pspNdf(21),
        pspNdr(22)
    }

cerRphyGroup OBJECT IDENTIFIER ::= { cerRphyMib 1 }

    cerRphyEnable   OBJECT-TYPE
        SYNTAX      TruthValue
        MAX-ACCESS  read-only
        STATUS      current
        DESCRIPTION
            "Whether or not RPHY is in use in this E6000 CER."
        DEFVAL { true }
        ::= { cerRphyGroup 1 }

    cerRphyMinMulticastSessionId OBJECT-TYPE
        SYNTAX      Unsigned32 (2147483649..2147549183)
        MAX-ACCESS  read-write
        STATUS      current
        DESCRIPTION
            "The minimum multicast session ID for this E6000."
        DEFVAL { 2147483649 }
        ::= { cerRphyGroup 2 }

    cerRphyMaxMulticastSessionId OBJECT-TYPE
        SYNTAX      Unsigned32 (2147483649..2147549183)
        MAX-ACCESS  read-write
        STATUS      current
        DESCRIPTION
            "The maximum multicast session ID for this E6000. Must be greater than
             Or equal cerMinMulticastSessionId"
        DEFVAL { 2147549183 }
        ::= { cerRphyGroup 3 }

    cerRphyLocalEventLogSize OBJECT-TYPE
        SYNTAX      Unsigned32 (5..50)
        MAX-ACCESS  read-write
        STATUS      current
        DESCRIPTION
            "The size in messages for the RPD-resident local event log."
        DEFVAL { 10 }
        ::= { cerRphyGroup 4 }

    cerRphyHistoryLogSize OBJECT-TYPE
        SYNTAX      Unsigned32 (100..1000)
        MAX-ACCESS  read-write
        STATUS      current
        DESCRIPTION
            "The size in messages of the RPD-resident local history log."
        DEFVAL { 200 }
        ::= { cerRphyGroup 5 }

    cerRphyL2TPv3Mtu OBJECT-TYPE
        SYNTAX      Unsigned32 (1280..2000)
        MAX-ACCESS  read-write
        STATUS      current
        DESCRIPTION
            "The MTU for RPD L2TPv3 tunnels."
        DEFVAL { 1982 }
        ::= { cerRphyGroup 6 }

    cerRphyEvThrottleAdminStatus OBJECT-TYPE
        SYNTAX INTEGER {
            unconstrained(1),
            maintainBelowThreshold(2),
            stopAtThreshold(3),
            inhibited(4)
        }
        MAX-ACCESS read-write
        STATUS      current
        DESCRIPTION
            "Controls the transmission of traps and syslog messages
             with respect to the trap pacing threshold.

             unconstrained(1) causes traps and syslog messages to be
             transmitted without regard to the threshold settings.

             maintainBelowThreshold(2) causes trap transmission and
             syslog messages to be suppressed if the number of traps
             would otherwise exceed the threshold.

             stopAtThreshold(3) causes trap transmission to cease at
             the threshold and not to resume until directed to do so.

             inhibited(4) causes all trap transmission and syslog
             messages to be suppressed.

             A single event is always treated as a single event for
             threshold counting.  That is, an event causing both a
             trap and a syslog message is still treated as a single
             event.

             Writing to this object resets the thresholding state."
        DEFVAL { unconstrained }
        ::= { cerRphyGroup 7 }

    cerRphyEvThrottleThreshold OBJECT-TYPE
        SYNTAX      Unsigned32
        UNITS       "events"
        MAX-ACCESS read-write
        STATUS      current
        DESCRIPTION
            "Number of events per docsDevEvThrottleInterval permitted
             before throttling is to occur.

             A single event, whether the notification could result in
             messages transmitted using syslog, SNMP, or both
             protocols, and regardless of the number of destinations,
             (including zero) is always treated as a single event for
             threshold counting.  For example, an event causing both
             a trap and a syslog message is still treated as a single
             event.

             All system notifications that occur within the device
             should be taken into consideration when calculating
             and monitoring the threshold."
        DEFVAL { 0 }
        ::= { cerRphyGroup 8 }

    cerRphyEvThrottleInterval OBJECT-TYPE
        SYNTAX      Integer32 (1..2147483647)
        UNITS       "seconds"
        MAX-ACCESS read-write
        STATUS      current
        DESCRIPTION
            "The interval over which docsDevEvThrottleThreshold
             applies."
        DEFVAL { 1 }
        ::= { cerRphyGroup 9 }

    cerRphyCoreLoopbackIfIndex OBJECT-TYPE
        SYNTAX  InterfaceIndexOrZero
        MAX-ACCESS  read-write
        STATUS  current
        DESCRIPTION
            "The Loopback ifIdex used to set the IP address for RPHY PWs. Is also
             used for the core IP address for all RPD GCP connections."
        DEFVAL { 0 }
        ::= { cerRphyGroup 10 }

    cerRphyCoreIpAddr OBJECT-TYPE
        SYNTAX  InetAddressIPv4or6
        MAX-ACCESS  read-only
        STATUS  current
        DESCRIPTION
            "Contains the E6000 Core IP address for RPHY PWs from the assigned
             Loopback interface. This address is also used as
             the core IP address for all RPD GCP connections."
        DEFVAL { ''H  }
        ::= { cerRphyGroup 11 }

    cerRphyMcastInterface   OBJECT-TYPE
        SYNTAX      InterfaceIndexOrZero
        MAX-ACCESS  read-write
        STATUS      current
        DESCRIPTION
            "The primary global NSI interface (LAG or Ethernet) for RPD multicasts."
        DEFVAL { 0 }
        ::= { cerRphyGroup 12 }

    cerRphyLowMcastIpAddr OBJECT-TYPE
        SYNTAX  InetAddressIPv4or6
        MAX-ACCESS  read-write
        STATUS  current
        DESCRIPTION
            "Contains the low multicast address for the range of 
             addresses used to multicast RPHY data packets to multiple
             RPDs."
        DEFVAL { ''H }
        ::= { cerRphyGroup 13 }

    cerRphyHighMcastIpAddr OBJECT-TYPE
        SYNTAX  InetAddressIPv4or6
        MAX-ACCESS  read-write
        STATUS  current
        DESCRIPTION
            "Contains the high multicast address for the range of 
             addresses used to multicast RPHY data packets to multiple
             RPDs."
        DEFVAL { ''H }
        ::= { cerRphyGroup 14 }

    cerRphyAllRpdMcastIpAddr OBJECT-TYPE
        SYNTAX  InetAddressIPv4or6
        MAX-ACCESS  read-write
        STATUS  current
        DESCRIPTION
            "Contains the multicast address for multicasts to every RPD. Type is 
             determined by cerRphyAddrType."
        DEFVAL { ''H }
        ::= { cerRphyGroup 15 }

    cerRphyGcpKeepAliveIntvl OBJECT-TYPE
        SYNTAX      Unsigned32 (1..10)
        UNITS       "seconds"
        MAX-ACCESS  read-write
        STATUS      current
        DESCRIPTION
            "How often the Core should send a keepalive message to each RPD."
        DEFVAL { 3 }
        ::= { cerRphyGroup 16 }

    cerRphyGcpKeepAliveTimeout OBJECT-TYPE
        SYNTAX      Unsigned32 (3..8)
        UNITS       "KeepAliveIntervals"
        MAX-ACCESS  read-write
        STATUS      current
        DESCRIPTION
            "How long the Core should wait to react to a missing 
             keepalive response message. TCP should compensate for 
             lost messages, so a timeout indicates that the RPD has failed
             or network connectivity is lost."
        DEFVAL { 3 }
        ::= { cerRphyGroup 17 }

    cerRphyL2TPv3HelloInterval OBJECT-TYPE
        SYNTAX      Unsigned32 (0|30..300)
        UNITS       "seconds"
        MAX-ACCESS  read-write
        STATUS      current
        DESCRIPTION
            "How long between L2TPv3 hello intervals. Zero disables L2TPv3 keep-alive messages."
        DEFVAL { 0 }
        ::= { cerRphyGroup 19 }

    cerRphyRpdJitterBufDepth OBJECT-TYPE
        SYNTAX      Unsigned32 (0|10|20|30|40|50)
        UNITS       "milliseconds"
        MAX-ACCESS  read-write
        STATUS      current
        DESCRIPTION
            "Jitter buffer depth in an RPD."
        DEFVAL { 10 }
        ::= { cerRphyGroup 20 }

    cerRphyRpdCoreType OBJECT-TYPE
        SYNTAX INTEGER {
            principal(1),
            aux(2)
        }
        MAX-ACCESS  read-write
        STATUS      current
        DESCRIPTION
            "Whether the E6000 CER is a principal core or auxiliary core."
        DEFVAL { principal }
        ::= { cerRphyGroup 21 }

    cerRphyMaxSsdAttempts OBJECT-TYPE
        SYNTAX      Unsigned32 (1..255)
        MAX-ACCESS  read-write
        STATUS      current
        DESCRIPTION
            "The maximum number of RPD SSD initiation attempts for the
             same software version without a successful RPD connection
             reporting that version as its running S/W version."
        DEFVAL { 3 }
        ::= { cerRphyGroup 22 }

    cerRphyRpdPollInterval OBJECT-TYPE
        SYNTAX      Unsigned32 (10..1440)
        UNITS      "seconds"
        MAX-ACCESS  read-write
        STATUS      current
        DESCRIPTION
            "The interval between background polls of RPD status."
        DEFVAL { 30 }
        ::= { cerRphyGroup 23 }

    cerRphyMcastBackupInterface   OBJECT-TYPE
        SYNTAX      InterfaceIndexOrZero
        MAX-ACCESS  read-write
        STATUS      current
        DESCRIPTION
            "The backup global NSI interface (LAG or Ethernet) for RPD multicast."
        DEFVAL { 0 }
        ::= { cerRphyGroup 24 }


    cerRphyMcastActiveInterface   OBJECT-TYPE
        SYNTAX      InterfaceIndexOrZero
        MAX-ACCESS  read-write
        STATUS      current
        DESCRIPTION
            "The active global NSI interface (LAG or Ethernet) for RPD multicast."
        DEFVAL { 0 }
        ::= { cerRphyGroup 25 }

    cerRphyMcastRevertToPrimaryInterface OBJECT-TYPE
        SYNTAX      TruthValue
        MAX-ACCESS  read-write
        STATUS      current
        DESCRIPTION
            "Whether or not to revert to the primary multicast interface if available."
        DEFVAL { true }
        ::= { cerRphyGroup 26 }

    cerRphyL2TPv3RetryCount OBJECT-TYPE
        SYNTAX      Unsigned32 (4..10)
        MAX-ACCESS  read-write
        STATUS      current
        DESCRIPTION
            "How many failed consecutive L2TPv3 retries there must be before an
             L2TPv3 tunnel is torn down."
        DEFVAL { 10 }
        ::= { cerRphyGroup 27 }

    cerRphyL2TPv3ConnectionSetupTimeout OBJECT-TYPE
        SYNTAX      Unsigned32 (5..300)
        UNITS       "seconds"
        MAX-ACCESS  read-write
        STATUS      current
        DESCRIPTION
            "How long to wait to set up all of the L2TPv3 tunnel(s) to an RPD."
        DEFVAL { 90 }
        ::= { cerRphyGroup 28 }

    cerRphyEnetPortAddrTimeout OBJECT-TYPE
        SYNTAX      Unsigned32 (2..60)
        UNITS       "seconds"
        MAX-ACCESS  read-write
        STATUS      current
        DESCRIPTION
            "How long to wait to successfully read TLV 100.15 and find all of
             the IP addresses for the RPD Ethernet ports."
        DEFVAL { 10 }
        ::= { cerRphyGroup 29 }

    cerRphyDlmMode OBJECT-TYPE
        SYNTAX INTEGER {
                disabled(1),
                measureOnly(2),
                twoTierAdaptive(3)
        }
        MAX-ACCESS  read-write
        STATUS      current
        DESCRIPTION
            "The mode for DOCSIS Latency Measurement (DLM)."
        DEFVAL { disabled }
        ::= { cerRphyGroup 30 }

    cerRphyIpAddrType OBJECT-TYPE
        SYNTAX  InetAddressType
        MAX-ACCESS  read-write
        STATUS  current
        DESCRIPTION
            "Contains the E6000 Core IP address family for cerRphyCoreLoopbackIfIndex.
            Only ipv4 and ipv6 are supported."
        DEFVAL { ipv6  }
        ::= { cerRphyGroup 31 }

--------------------------------------------------------------------------------------------------
-- RPD Index table
--------------------------------------------------------------------------------------------------

cerRpdIndexTable OBJECT-TYPE
    SYNTAX SEQUENCE OF CerRpdIndexEntry
    MAX-ACCESS not-accessible
    STATUS current
    DESCRIPTION
        "This table maps the global RPD index to the RPD name."
    ::= { cerRphyMib 3 }

cerRpdIndexEntry OBJECT-TYPE
    SYNTAX CerRpdIndexEntry
    MAX-ACCESS not-accessible
    STATUS current
    DESCRIPTION
        "An entry for the RPD Index table."
    INDEX { cerRpdIndexRpdIndex }
    ::= {cerRpdIndexTable 1}

CerRpdIndexEntry ::= SEQUENCE {
    cerRpdIndexRpdIndex      CerRpdIndex,
    cerRpdIndexRpdName       CerRpdName
}

cerRpdIndexRpdIndex OBJECT-TYPE
    SYNTAX CerRpdIndex 
    MAX-ACCESS accessible-for-notify
    STATUS current
    DESCRIPTION
        "RPD global index used in the RPD ifIndex of the PHY-layer channel."
    ::= {cerRpdIndexEntry 1}

cerRpdIndexRpdName OBJECT-TYPE
    SYNTAX CerRpdName
    MAX-ACCESS read-only
    STATUS current
    DESCRIPTION
        "The name of the RPD."
    ::= {cerRpdIndexEntry 2}


--------------------------------------------------------------------------------------------------
-- RPD MAC Address table
--------------------------------------------------------------------------------------------------

cerRpdMacAddrTable OBJECT-TYPE
    SYNTAX SEQUENCE OF CerRpdMacAddrEntry
    MAX-ACCESS not-accessible
    STATUS current
    DESCRIPTION
        "This table maps the global RPD MAC Address to the RPD name."
    ::= { cerRphyMib 4 }

cerRpdMacAddrEntry OBJECT-TYPE
    SYNTAX CerRpdMacAddrEntry
    MAX-ACCESS not-accessible
    STATUS current
    DESCRIPTION
        "An entry for the RPD MAC Address table."
    INDEX { cerRpdMacAddr }
    ::= {cerRpdMacAddrTable 1}

CerRpdMacAddrEntry ::= SEQUENCE {
    cerRpdMacAddr              MacAddress,
    cerRpdMacAddrName          CerRpdName
}

cerRpdMacAddr OBJECT-TYPE
    SYNTAX MacAddress
    MAX-ACCESS not-accessible
    STATUS current
    DESCRIPTION
        "RPD MAC address used as global RPD ID."
    ::= {cerRpdMacAddrEntry 1}

cerRpdMacAddrName OBJECT-TYPE
    SYNTAX CerRpdName
    MAX-ACCESS read-only
    STATUS current
    DESCRIPTION
        "The name of the RPD."
    ::= {cerRpdMacAddrEntry 2}

--------------------------------------------------------------------------------------------------
-- RPD Downstream RF Port Configuration table
--------------------------------------------------------------------------------------------------
cerRpdDsRfPortTable OBJECT-TYPE
    SYNTAX SEQUENCE OF CerRpdDsRfPortEntry
    MAX-ACCESS not-accessible
    STATUS current
    DESCRIPTION
        "This table contains RPD base power level per equivalent channel
         In Tenths of dBmV."
    ::= { cerRphyMib 5 }

cerRpdDsRfPortEntry OBJECT-TYPE
    SYNTAX CerRpdDsRfPortEntry
    MAX-ACCESS not-accessible
    STATUS current
    DESCRIPTION
        "An entry for the table."
    INDEX { cerRpdDsRfPortRpdIndex, cerRpdDsRfPortRpdRfPortId }
    ::= {cerRpdDsRfPortTable 1}

CerRpdDsRfPortEntry ::= SEQUENCE {
    cerRpdDsRfPortRpdIndex              CerRpdIndex,
    cerRpdDsRfPortRpdRfPortId           Unsigned32,
    cerRpdDsRfPortBasePower             TenthdBmV,
    cerRpdDsRfPortTilt                  TenthdB,
    cerRpdDsRfPortTiltMaxFreq           Unsigned32,
    cerRpdDsRfPortMeasuredPower         Unsigned32
}

cerRpdDsRfPortRpdIndex OBJECT-TYPE
    SYNTAX CerRpdIndex
    MAX-ACCESS not-accessible
    STATUS current
    DESCRIPTION
        "Global index for this RPD."
    ::= { cerRpdDsRfPortEntry 1 }

cerRpdDsRfPortRpdRfPortId OBJECT-TYPE
    SYNTAX Unsigned32 (1..4)
    MAX-ACCESS not-accessible
    STATUS current
    DESCRIPTION
        "Index of DS RF port on the RPD."
    ::= { cerRpdDsRfPortEntry 2}

cerRpdDsRfPortBasePower OBJECT-TYPE
    SYNTAX      TenthdBmV (0|260..450)
    UNITS       "dBmV"
    MAX-ACCESS  read-write
    STATUS      current
    DESCRIPTION
        "The RPD RF port operational transmit power.  If this
         interface does not support output power control then
         this object will return 0 and be treated as read-only.
         If the interface is down, this object either returns
         the configured value or the value of 0.  See the 
         reference for recommended and required power levels.
         Sent to the RPD using TLV 61.3."
    REFERENCE
        "DOCSIS Radio Frequency Interface Specification,
         Table 4-12 and Table 4-13."
    DEFVAL { 260 }
    ::= { cerRpdDsRfPortEntry 3 }

cerRpdDsRfPortTilt OBJECT-TYPE
    SYNTAX      TenthdB (0..160)
    UNITS       "TenthdB"
    MAX-ACCESS  read-write
    STATUS      current
    DESCRIPTION
        "The RPD RF port tilt across the tilt region. Sent to the RPD using TLV 61.5."
    DEFVAL { 0 }
    ::= { cerRpdDsRfPortEntry 4 }

cerRpdDsRfPortTiltMaxFreq OBJECT-TYPE
    SYNTAX     Unsigned32
    UNITS      "Hertz"
    MAX-ACCESS read-write
    STATUS current
    DESCRIPTION
        "The maximum frequency for applying tilt. The default is the the high edge 
         of the OFDM channel frequency range. The low edge of the tilt region is 
         always 108 MHz, the low edge of the OFDM frequency range.
         Sent to the RPD using TLV 61.6"
    DEFVAL { 1218000000 }
    ::= { cerRpdDsRfPortEntry 5 }
    
cerRpdDsRfPortMeasuredPower OBJECT-TYPE
    SYNTAX      Unsigned32 (0|260..450)
    UNITS       "TenthdBmV"
    MAX-ACCESS  read-only
    STATUS current
    DESCRIPTION
        "The last reported value of the RPD RF port measured 
         transmit power.  If this interface does not receive measured 
         transmit power then this object will return 0.
         If the interface is down, this object returns
         value of 0."
    REFERENCE
        "Customer Specific TLV drives this parameter."
    DEFVAL { 0 }
    ::= { cerRpdDsRfPortEntry 6 }

--------------------------------------------------------------------------------------------------
-- RPD Name table
--------------------------------------------------------------------------------------------------

cerRpdNameTable OBJECT-TYPE
    SYNTAX SEQUENCE OF CerRpdNameEntry
    MAX-ACCESS not-accessible
    STATUS current
    DESCRIPTION
        "This table contains the RPD configuration for all RPDs."
    ::= { cerRphyMib 6 }

cerRpdNameEntry OBJECT-TYPE
    SYNTAX CerRpdNameEntry
    MAX-ACCESS not-accessible
    STATUS current
    DESCRIPTION
        "An entry for the RPD table."
    INDEX { cerRpdName }
    ::= {cerRpdNameTable 1}

CerRpdNameEntry ::= SEQUENCE {
    cerRpdName                           OCTET STRING,
    cerRpdNameRpdIndex                   CerRpdIndexOrZero,
    cerRpdNameMacAddr                    MacAddress,
    cerRpdNameDescription                DisplayString,
    cerRpdNameDcamCardId                 Unsigned32,
    cerRpdNameUcamCardId                 Unsigned32,
    cerRpdNameAdminState                 AdminState,
    cerRpdNameCinLatency                 Unsigned32,
    cerRpdNameSsdEnable                  TruthValue,
    cerRpdNameDtiMapAdj                  Unsigned32,
    cerRpdNameRowStatus                  RowStatus,
    cerRpdNameResetRpd                   INTEGER,
    cerRpdNameStatusPoll                 TruthValue,
    cerRpdNameAdpEnabled                 TruthValue,
    cerRpdNameAdpAutoRevert              TruthValue,
    cerRpdNameAdpHdTimeout               Unsigned32,
    cerRpdNameAdpIntervalTime            Unsigned32,
    cerRpdNameLcceMode                   INTEGER
}

cerRpdName OBJECT-TYPE
    SYNTAX OCTET STRING(SIZE(2..16))
    MAX-ACCESS not-accessible
    STATUS current
    DESCRIPTION
        "The name of the RPD."
    ::= {cerRpdNameEntry 1}

cerRpdNameRpdIndex OBJECT-TYPE
    SYNTAX CerRpdIndexOrZero
    MAX-ACCESS read-create
    STATUS current
    DESCRIPTION
        "RPD global index used in the RPD ifIndex of the PHY-layer channel.
         Set internally to a unique number if not provided."
    ::= { cerRpdNameEntry 2 }

cerRpdNameMacAddr OBJECT-TYPE 
   SYNTAX       MacAddress
   MAX-ACCESS   read-create
   STATUS       current
   DESCRIPTION
       "Contains a MAC address used to globally identify the RPD."
   DEFVAL { '000000000000'H }
   ::= { cerRpdNameEntry 3 } 

cerRpdNameDescription OBJECT-TYPE 
   SYNTAX       DisplayString (SIZE(0..100))
   MAX-ACCESS   read-create
   STATUS       current
   DESCRIPTION
       "Contains a text description of RPD."
   DEFVAL { "" }
   ::= { cerRpdNameEntry 4 } 

cerRpdNameDcamCardId OBJECT-TYPE
    SYNTAX Unsigned32 (0..6|9..14)
    MAX-ACCESS read-create
    STATUS current
    DESCRIPTION
        "The card number of the DCAM controlling this RPD. Must be set to use the RPD.
         Zero means unassigned."
    DEFVAL { 0 }
    ::= {cerRpdNameEntry 6}

cerRpdNameUcamCardId OBJECT-TYPE
    SYNTAX Unsigned32 (0..6|9..14)
    MAX-ACCESS read-create
    STATUS current
    DESCRIPTION
        "The card number of the UCAM controlling this RPD. Must be set to use the RPD. 
         Zero means unassigned."
    DEFVAL { 0 }
    ::= {cerRpdNameEntry 7}

cerRpdNameAdminState OBJECT-TYPE
    SYNTAX      AdminState
    MAX-ACCESS  read-create
    STATUS      current
    DESCRIPTION
        "This is the administrative state of this RPD."
     DEFVAL { down }
    ::= { cerRpdNameEntry 8 }

cerRpdNameCinLatency OBJECT-TYPE
    SYNTAX Unsigned32 (0..20000)
    UNITS "microseconds"
    MAX-ACCESS read-create
    STATUS current
    DESCRIPTION
        " The number of micro-seconds of downstream latency caused by the CIN.
        800us is equivalent to a fiber propagation delay of 100 miles one-way."
    DEFVAL { 1600 }
    ::= { cerRpdNameEntry 9 }

cerRpdNameSsdEnable OBJECT-TYPE
    SYNTAX      TruthValue
    MAX-ACCESS  read-create
    STATUS      current
    DESCRIPTION
        "Whether or not to update the RPD to the SW file in cerRpdNameSwFileName. "
     DEFVAL { false }
    ::= { cerRpdNameEntry 10 }

cerRpdNameDtiMapAdj OBJECT-TYPE
    SYNTAX Unsigned32 (0..2000)
    UNITS "microseconds"
    MAX-ACCESS read-create
    STATUS current
    DESCRIPTION
        "The number of micro-seconds of map adjustment due to the 1588 DTI clock
         difference between the RPD and the CCAP core."
    DEFVAL { 1000 }
    ::= { cerRpdNameEntry 11 }

cerRpdNameRowStatus   OBJECT-TYPE
    SYNTAX      RowStatus
    MAX-ACCESS  read-create
    STATUS      current
    DESCRIPTION
        "The RowStatus for controlling entries in this table. 
         Allowed values are createAndGo, destroy, and active."
    ::= { cerRpdNameEntry 12 }

cerRpdNameResetRpd OBJECT-TYPE
    SYNTAX INTEGER {
        none(0),
        soft(1),
        hard(2),
        nvram(3),
        factory(4)
    }
    MAX-ACCESS  read-create
    STATUS      current
    DESCRIPTION
        "Always reads as none. Setting it to one of the other values results
        a reset GCP TLV being sent to the RPD with that value. 
        Setting it to none has no effect."
    DEFVAL { none }
    ::= { cerRpdNameEntry 13 }

cerRpdNameStatusPoll OBJECT-TYPE
    SYNTAX TruthValue
    MAX-ACCESS  read-create
    STATUS      current
    DESCRIPTION
        "The object is used to trigger an immediate poll of a
         status from this RPD by setting it to true. This object always 
         read back as a value of false. When the poll is finished, the 
         value of sysUpTime is saved in cerRpdDataLastStatusRead for the RPD."
    DEFVAL { false }
    ::= { cerRpdNameEntry 14 }
    
cerRpdNameAdpEnabled OBJECT-TYPE
    SYNTAX TruthValue
    MAX-ACCESS read-create
    STATUS current
    DESCRIPTION
        "The object is used to enable or disable ARRIS Discovery Protocol (ADP)."
    DEFVAL { true }
    ::= { cerRpdNameEntry 15 }

cerRpdNameAdpAutoRevert OBJECT-TYPE
    SYNTAX TruthValue
    MAX-ACCESS read-create
    STATUS current
    DESCRIPTION
        "The object is used to enable or disable auto-revertive behavior for ADP."
    DEFVAL { false }
    ::= { cerRpdNameEntry 16 }

cerRpdNameAdpHdTimeout OBJECT-TYPE
    SYNTAX Unsigned32 (60..120)
    UNITS "seconds"
    MAX-ACCESS read-create
    STATUS current
    DESCRIPTION
        "Maximum time, in seconds, ADP waits for ADP advertisements from its
         neighbors."
    DEFVAL { 60 }
    ::= { cerRpdNameEntry 17 }

cerRpdNameAdpIntervalTime OBJECT-TYPE
    SYNTAX Unsigned32 (1..60)
    UNITS "seconds"
    MAX-ACCESS read-create
    STATUS current
    DESCRIPTION
        "Time, in seconds, between ADP advertisement messages sent by ADP."
    DEFVAL { 1 }
    ::= { cerRpdNameEntry 18 }

cerRpdNameLcceMode OBJECT-TYPE
    SYNTAX INTEGER {
        singleLcce(1),
        dualLcce(2)
    }
    MAX-ACCESS read-create
    STATUS current
    DESCRIPTION
        "Controls the number of L2TPv3 tunnels to an RPD. In dualLcee mode,
         each tunnel is to a different RPD Ethernet port and address.
         singleLcce(1): set up only one L2TPv3 tunnel to the RPD using the
         address first used for GCP, even if the RPD has more than one Ethernet
         port. All channels and CW tones will use that tunnel.
         dualLcce(2): set up a separate tunnel to each Ethernet port for the
         RPD with two Ethernet ports.
         If the RPD only supports one Ethernet port, or the second port is not
         L3 functional at initialization, fail RPD configuration."
    DEFVAL { singleLcce }
    ::= { cerRpdNameEntry 19 }

--
-- The following table globally controls the reporting of the various classes
-- of events from RPDs.
--

cerRpdGlobalEvControlTable OBJECT-TYPE
    SYNTAX      SEQUENCE OF CerRpdGlobalEvControlEntry
    MAX-ACCESS  not-accessible
    STATUS      current
    DESCRIPTION
        "This table allows control of the reporting of RPD event
         classes. This table globally controls event reporting for
         all RPDs in the E6000.

         For each event priority, a combination of
         logging and reporting mechanisms may be chosen.  The
         mapping of event types to priorities is
         vendor dependent.  Vendors may also choose to allow
         the user to control that mapping through proprietary
         means.  Table entries MUST persist across reboots for
         CMTS devices and MUST NOT persist across reboots for CM
         devices."
    ::= { cerRphyMib 7 }

cerRpdGlobalEvControlEntry OBJECT-TYPE
    SYNTAX      CerRpdGlobalEvControlEntry
    MAX-ACCESS  not-accessible
    STATUS      current
    DESCRIPTION
        "Allows configuration of the reporting mechanisms for a
         particular event priority."
    INDEX { cerRpdGlobalEvPriority }
    ::= { cerRpdGlobalEvControlTable 1 }

CerRpdGlobalEvControlEntry ::= SEQUENCE {
    cerRpdGlobalEvPriority        INTEGER,
    cerRpdGlobalEvReporting       BITS
    }

cerRpdGlobalEvPriority OBJECT-TYPE
    SYNTAX INTEGER {
        emergency(1),
        alert(2),
        critical(3),
        error(4),
        warning(5),
        notice(6),
        information(7),
        debug(8)
    }
    MAX-ACCESS  not-accessible
    STATUS      current
    DESCRIPTION
        "The priority level that is controlled by this
         entry.  These are ordered from most (emergency) to least
         (debug) critical.  Each event with a CM or CMTS has a
         particular priority level associated with it (as defined
         by the vendor).

         emergency(1) events indicate vendor-specific fatal
         hardware or software errors that prevent normal system
         operation.

         alert(2) events indicate a serious failure that causes
         the reporting system to reboot but is not caused by
         hardware or software malfunctioning.

         critical(3) events indicate a serious failure that
         requires attention and prevents the device from
         transmitting data but that could be recovered without
         rebooting the system.

         error(4) and warning(5) events indicate that a failure
         occurred that could interrupt the normal data flow but
         that does not cause the device to re-register.

         notice(6) and information(7) events indicate a
         milestone or checkpoint in normal operation that could
         be of particular importance for troubleshooting.

         debug(8) events are reserved for vendor-specific
         events.

         During normal operation, no event more
         critical than notice(6) should be generated.  Events
         between warning and emergency should be generated at
         appropriate levels of problems (e.g., emergency when the
         box is about to crash)."
    ::= { cerRpdGlobalEvControlEntry 1 }

cerRpdGlobalEvReporting OBJECT-TYPE
        SYNTAX BITS {
            localVolatile(0),
            gcpEvent(1)
        }
        MAX-ACCESS  read-write
        STATUS      current
        DESCRIPTION
            "Defines the action to be taken on occurrence of this
             event class. If the localVolatile(1) bit is set, then
             log to the internal log. If the gcpEvent(2) bit is set, 
             then a send a GCP event message for the event."
        DEFVAL { { localVolatile, gcpEvent } }
        ::= { cerRpdGlobalEvControlEntry 2 }


--
-- The following table controls per RPD the reporting of the various classes
-- of events from RPDs. If no corresponding row for an RPD/priority exists,
-- the cerRpdGlobalEvControlTable controls reporting behavior for that
-- RPD/priority. 
--

cerRpdEvControlTable OBJECT-TYPE
    SYNTAX      SEQUENCE OF CerRpdEvControlEntry
    MAX-ACCESS  not-accessible
    STATUS      current
    DESCRIPTION
        "This table allows control of the reporting of RPD event
         classes. This table controls event reporting for
         a single RPD in the E6000.

         For each event priority, a combination of
         logging and reporting mechanisms may be chosen.  The
         mapping of event types to priorities is
         vendor dependent.  Vendors may also choose to allow
         the user to control that mapping through proprietary
         means.  Table entries MUST persist across reboots for
         CMTS devices and MUST NOT persist across reboots for CM
         devices."
    ::= { cerRphyMib 8 }

cerRpdEvControlEntry OBJECT-TYPE
    SYNTAX      CerRpdEvControlEntry
    MAX-ACCESS  not-accessible
    STATUS      current
    DESCRIPTION
        "Allows configuration of the reporting mechanisms for a
         particular event priority on a particular RPD."
    INDEX { cerRpdEvRpdIndex, cerRpdEvPriority }
    ::= { cerRpdEvControlTable 1 }

CerRpdEvControlEntry ::= SEQUENCE {
        cerRpdEvRpdIndex        CerRpdIndex,
        cerRpdEvPriority        INTEGER,
        cerRpdEvReporting       BITS,
        cerRpdEvRowStatus       RowStatus
    }

cerRpdEvRpdIndex OBJECT-TYPE
    SYNTAX CerRpdIndex
    MAX-ACCESS not-accessible
    STATUS current
    DESCRIPTION
        "RPD global index."
    ::= { cerRpdEvControlEntry 1 }

cerRpdEvPriority OBJECT-TYPE
    SYNTAX INTEGER {
        emergency(1),
        alert(2),
        critical(3),
        error(4),
        warning(5),
        notice(6),
        information(7),
        debug(8)
    }
    MAX-ACCESS  not-accessible
    STATUS      current
    DESCRIPTION
        "The priority level that is controlled by this
         entry.  These are ordered from most (emergency) to least
         (debug) critical.  Each event with a CM or CMTS has a
         particular priority level associated with it (as defined
         by the vendor).

         emergency(1) events indicate vendor-specific fatal
         hardware or software errors that prevent normal system
         operation.

         alert(2) events indicate a serious failure that causes
         the reporting system to reboot but is not caused by
         hardware or software malfunctioning.

         critical(3) events indicate a serious failure that
         requires attention and prevents the device from
         transmitting data but that could be recovered without
         rebooting the system.

         error(4) and warning(5) events indicate that a failure
         occurred that could interrupt the normal data flow but
         that does not cause the device to re-register.

         notice(6) and information(7) events indicate a
         milestone or checkpoint in normal operation that could
         be of particular importance for troubleshooting.

         debug(8) events are reserved for vendor-specific
         events.

         During normal operation, no event more
         critical than notice(6) should be generated.  Events
         between warning and emergency should be generated at
         appropriate levels of problems (e.g., emergency when the
         box is about to crash)."
    ::= { cerRpdEvControlEntry 2 }

cerRpdEvReporting OBJECT-TYPE
    SYNTAX BITS {
        localVolatile(0),
        gcpEvent(1)
    }
    MAX-ACCESS  read-create
    STATUS      current
    DESCRIPTION
        "Defines the action to be taken on occurrence of this
         event class. If the localVolatile(1) bit is set, then
         log to the internal log. If the gcpEvent(2) bit is set, 
         then a send a GCP event message for the event."
    DEFVAL { { localVolatile, gcpEvent } }
    ::= { cerRpdEvControlEntry 3 }

cerRpdEvRowStatus   OBJECT-TYPE
    SYNTAX      RowStatus
    MAX-ACCESS  read-create
    STATUS      current
    DESCRIPTION
        "The RowStatus for controlling entries in this table. 
         Allowed values are createAndGo, destroy, and active."
    ::= { cerRpdEvControlEntry 4 }

--------------------------------------------------------------------------------------------------
-- Fiber Node DS RF Port List table
--------------------------------------------------------------------------------------------------
cerFnDsRfPortTable OBJECT-TYPE
    SYNTAX SEQUENCE OF CerFnDsRfPortEntry
    MAX-ACCESS not-accessible
    STATUS current
    DESCRIPTION
        "This table contains the list of DS RPD RF ports assigned to a FN."
    ::= { cerRphyMib 9 }

cerFnDsRfPortEntry OBJECT-TYPE
    SYNTAX CerFnDsRfPortEntry
    MAX-ACCESS not-accessible
    STATUS current
    DESCRIPTION
        "An entry for the table."
    INDEX { cerFnDsRfPortFnName, cerFnDsRfPortRpdIndex, cerFnDsRfPortRpdPortId }
    ::= {cerFnDsRfPortTable 1}

CerFnDsRfPortEntry ::= SEQUENCE {
    cerFnDsRfPortFnName                     NodeName,
    cerFnDsRfPortRpdIndex                   CerRpdIndex,
    cerFnDsRfPortRpdPortId                  Unsigned32,
    cerFnDsRfPortRowStatus                  RowStatus
}

cerFnDsRfPortFnName OBJECT-TYPE
    SYNTAX NodeName
    MAX-ACCESS not-accessible
    STATUS current
    DESCRIPTION
        "Name of the Fiber node."
    ::= { cerFnDsRfPortEntry 1 }

cerFnDsRfPortRpdIndex OBJECT-TYPE
    SYNTAX CerRpdIndex
    MAX-ACCESS not-accessible
    STATUS current
    DESCRIPTION
        "The index of the RPD."
    ::= {cerFnDsRfPortEntry 2}

cerFnDsRfPortRpdPortId OBJECT-TYPE
    SYNTAX Unsigned32 (1..4)
    MAX-ACCESS not-accessible
    STATUS current
    DESCRIPTION
        "The RF port number on the RPD for this channel."
    ::= {cerFnDsRfPortEntry 3}

cerFnDsRfPortRowStatus   OBJECT-TYPE
    SYNTAX      RowStatus
    MAX-ACCESS  read-create
    STATUS      current
    DESCRIPTION
        "The RowStatus for controlling entries in this table. 
         Allowed values are createAndGo, destroy, and active."
    ::= { cerFnDsRfPortEntry 4 }

--------------------------------------------------------------------------------------------------
-- Video RPD Group DS RF Port List table
--------------------------------------------------------------------------------------------------
cerVideoRpdDsRfPortTable OBJECT-TYPE
    SYNTAX SEQUENCE OF CerVideoRpdDsRfPortEntry
    MAX-ACCESS not-accessible
    STATUS current
    DESCRIPTION
        "This table contains the list of DS RPD RF ports assigned to a video RPD group."
    ::= { cerRphyMib 10 }

cerVideoRpdDsRfPortEntry OBJECT-TYPE
    SYNTAX CerVideoRpdDsRfPortEntry
    MAX-ACCESS not-accessible
    STATUS current
    DESCRIPTION
        "An entry for the table."
    INDEX { cerVideoRpdDsRfPortRpdGrpName, cerVideoRpdDsRfPortRpdIndex, cerVideoRpdDsRfPortRpdPortId }
    ::= {cerVideoRpdDsRfPortTable 1}

CerVideoRpdDsRfPortEntry ::= SEQUENCE {
    cerVideoRpdDsRfPortRpdGrpName         DsVidGrpName,
    cerVideoRpdDsRfPortRpdIndex           CerRpdIndexOrZero,
    cerVideoRpdDsRfPortRpdPortId          Unsigned32,
    cerVideoRpdDsRfPortRowStatus          RowStatus
}

cerVideoRpdDsRfPortRpdGrpName OBJECT-TYPE
    SYNTAX DsVidGrpName
    MAX-ACCESS not-accessible
    STATUS current
    DESCRIPTION
        "Name of the DS video RPD group."
    ::= { cerVideoRpdDsRfPortEntry 1}

cerVideoRpdDsRfPortRpdIndex OBJECT-TYPE
    SYNTAX CerRpdIndexOrZero
    MAX-ACCESS not-accessible
    STATUS current
    DESCRIPTION
        "The index of the assigned RPD. Zero means all RPDs are in this group."
    ::= {cerVideoRpdDsRfPortEntry 2}

cerVideoRpdDsRfPortRpdPortId OBJECT-TYPE
    SYNTAX Unsigned32 (0..4)
    MAX-ACCESS not-accessible
    STATUS current
    DESCRIPTION
        "The RF port number on the RPD for this channel.
         Zero means all DS RF port on the RPD(s)."
    ::= {cerVideoRpdDsRfPortEntry 3}

cerVideoRpdDsRfPortRowStatus   OBJECT-TYPE
    SYNTAX      RowStatus
    MAX-ACCESS  read-create
    STATUS      current
    DESCRIPTION
        "The RowStatus for controlling entries in this table. 
         Allowed values are createAndGo, destroy, and active."
    ::= { cerVideoRpdDsRfPortEntry 4 }

--------------------------------------------------------------------------------------------------
-- Fiber Node US RF Port List table
--------------------------------------------------------------------------------------------------
cerFnUsRfPortTable OBJECT-TYPE
    SYNTAX SEQUENCE OF CerFnUsRfPortEntry
    MAX-ACCESS not-accessible
    STATUS current
    DESCRIPTION
        "This table contains the list of US RPD RF ports assigned to a FN."
    ::= { cerRphyMib 11 }

cerFnUsRfPortEntry OBJECT-TYPE
    SYNTAX CerFnUsRfPortEntry
    MAX-ACCESS not-accessible
    STATUS current
    DESCRIPTION
        "An entry for the table."
    INDEX { cerFnUsRfPortFnName, cerFnUsRfPortRpdIndex, cerFnUsRfPortRpdPortId }
    ::= {cerFnUsRfPortTable 1}

CerFnUsRfPortEntry ::= SEQUENCE {
    cerFnUsRfPortFnName                     NodeName,
    cerFnUsRfPortRpdIndex                   CerRpdIndex,
    cerFnUsRfPortRpdPortId                  Unsigned32,
    cerFnUsRfPortRowStatus                  RowStatus
}

cerFnUsRfPortFnName OBJECT-TYPE
    SYNTAX NodeName
    MAX-ACCESS not-accessible
    STATUS current
    DESCRIPTION
        "Name of the Fiber node."
    ::= { cerFnUsRfPortEntry 1 }

cerFnUsRfPortRpdIndex OBJECT-TYPE
    SYNTAX CerRpdIndex
    MAX-ACCESS not-accessible
    STATUS current
    DESCRIPTION
        "The index of the RPD."
    ::= {cerFnUsRfPortEntry 2}

cerFnUsRfPortRpdPortId OBJECT-TYPE
    SYNTAX Unsigned32 (1..4)
    MAX-ACCESS not-accessible
    STATUS current
    DESCRIPTION
        "The RF port number on the RPD for this channel."
    ::= {cerFnUsRfPortEntry 3}

cerFnUsRfPortRowStatus   OBJECT-TYPE
    SYNTAX      RowStatus
    MAX-ACCESS  read-create
    STATUS      current
    DESCRIPTION
        "The RowStatus for controlling entries in this table. 
         Allowed values are createAndGo, destroy, and active."
    ::= { cerFnUsRfPortEntry 4 }

--------------------------------------------------------------------------------------------------
--========================= cerRpdDsScQamTable =========================
--------------------------------------------------------------------------------------------------

cerRpdDsScQamTable OBJECT-TYPE
    SYNTAX      SEQUENCE OF CerRpdDsScQamEntry
    MAX-ACCESS  not-accessible
    STATUS      current
    DESCRIPTION
        "This status table contains the SC-QAM PHY channels on an RPD."
    ::= { cerRphyMib 14 }

cerRpdDsScQamEntry OBJECT-TYPE
    SYNTAX      CerRpdDsScQamEntry
    MAX-ACCESS  not-accessible
    STATUS      current
    DESCRIPTION
        "An entry contains one RPD SC-QAM channel."
    INDEX { cerRpdDsScQamRpdIndex, cerRpdDsScQamRpdChanIfIndex }
    ::= { cerRpdDsScQamTable 1 }

CerRpdDsScQamEntry ::= SEQUENCE {
            cerRpdDsScQamRpdIndex            CerRpdIndex,
            cerRpdDsScQamRpdChanIfIndex      InterfaceIndex,
            cerRpdDsScQamCoreChanIfIndex     InterfaceIndex,
            cerRpdDsScQamRpdChanSelector     Unsigned32,
            cerRpdDsScQamRpdDepiChanId       Unsigned32,
            cerRpdDsScQamDataPwId            Unsigned32
        }

cerRpdDsScQamRpdIndex OBJECT-TYPE
    SYNTAX CerRpdIndex
    MAX-ACCESS not-accessible
    STATUS current
    DESCRIPTION
        "The index of the RPD."
    ::= { cerRpdDsScQamEntry 1 }

cerRpdDsScQamRpdChanIfIndex OBJECT-TYPE
    SYNTAX     InterfaceIndex
    MAX-ACCESS not-accessible
    STATUS     current
    DESCRIPTION
        "The PHY channel ifIndex of this downstream SC-QAM channel."
    ::= { cerRpdDsScQamEntry 2 }

cerRpdDsScQamCoreChanIfIndex OBJECT-TYPE
    SYNTAX      InterfaceIndex
    MAX-ACCESS  read-only
    STATUS      current
    DESCRIPTION
        "The MAC channel ifIndex for this downstream SC-QAMchannel."
    ::= { cerRpdDsScQamEntry 3 }

cerRpdDsScQamRpdChanSelector OBJECT-TYPE
    SYNTAX Unsigned32
    MAX-ACCESS   read-only
    STATUS current
    DESCRIPTION
        "DEPI channel selector for this OFDM channel on the RPD. This 24 bit number
         has the RPD RF port number in the upper 8 bits, the channel type in
         the middle 8 bits, and the channel ID in low 8 bits."
    REFERENCE
        "DEPI Table 9"
    ::= { cerRpdDsScQamEntry 4 }

cerRpdDsScQamRpdDepiChanId OBJECT-TYPE
    SYNTAX Unsigned32 (0..255)
    MAX-ACCESS   read-only
    STATUS current
    DESCRIPTION
        "DEPI channel ID associated with this RPD channel selector.
         Zero means that this channel selector channel type does not
         use a DEPI channel ID (only DOCSIS DS channels have a channel ID)."
    ::= { cerRpdDsScQamEntry 5 }

cerRpdDsScQamDataPwId OBJECT-TYPE
    SYNTAX          Unsigned32 (1..4294967295)
    MAX-ACCESS      read-only
    STATUS          current
    DESCRIPTION
        "The Core ID of the data pseudo-wire carrying the SC-QAM channel." 
    ::= { cerRpdDsScQamEntry 6 }

--========================= cerRpdDsOfdmChanTable =========================

cerRpdDsOfdmChanTable OBJECT-TYPE
    SYNTAX      SEQUENCE OF CerRpdDsOfdmChanEntry
    MAX-ACCESS  not-accessible
    STATUS      current
    DESCRIPTION
        "This status table contains OFDM channels on an RPD."
    ::= { cerRphyMib 15 }

cerRpdDsOfdmChanEntry OBJECT-TYPE
    SYNTAX      CerRpdDsOfdmChanEntry
    MAX-ACCESS  not-accessible
    STATUS      current
    DESCRIPTION
        "An entry shows one DS OFDM RPD channel."
    INDEX { cerRpdDsOfdmChanRpdIndex, cerRpdDsOfdmChanRpdChanIfIndex }
    ::= { cerRpdDsOfdmChanTable 1 }

CerRpdDsOfdmChanEntry ::= SEQUENCE {
        cerRpdDsOfdmChanRpdIndex            CerRpdIndex,
        cerRpdDsOfdmChanRpdChanIfIndex      InterfaceIndex,
        cerRpdDsOfdmChanCoreChanIfIndex     InterfaceIndex,
        cerRpdDsOfdmChanRpdChanSelector     Unsigned32,
        cerRpdDsOfdmChanRpdDepiChanId       Unsigned32,
        cerRpdDsOfdmChanDataPwId            Unsigned32,
        cerRpdDsOfdmChanRpdPlcChanSelector  Unsigned32
        }

cerRpdDsOfdmChanRpdIndex OBJECT-TYPE
    SYNTAX CerRpdIndex
    MAX-ACCESS not-accessible
    STATUS current
    DESCRIPTION
        "The index of the RPD."
    ::= { cerRpdDsOfdmChanEntry 1}

cerRpdDsOfdmChanRpdChanIfIndex OBJECT-TYPE
    SYNTAX     InterfaceIndex
    MAX-ACCESS not-accessible
    STATUS     current
    DESCRIPTION
        "The ifIndex of this downstream OFDM RPD channel."
    ::= { cerRpdDsOfdmChanEntry 2 }

cerRpdDsOfdmChanCoreChanIfIndex OBJECT-TYPE
    SYNTAX      InterfaceIndex
    MAX-ACCESS  read-only
    STATUS      current
    DESCRIPTION
        "The ifIndex of the MAC channel for this OFDM channel."
    ::= { cerRpdDsOfdmChanEntry 3 }

cerRpdDsOfdmChanRpdChanSelector OBJECT-TYPE
    SYNTAX Unsigned32
    MAX-ACCESS   read-only
    STATUS current
    DESCRIPTION
        "DEPI non-PLC channel selector for this OFDM channel on the RPD. This 24 bit number
         has the RPD RF port number in the upper 8 bits, the channel type in
         the middle 8 bits, and the channel ID in low 8 bits."
    REFERENCE
        "DEPI Table 9"
    ::= { cerRpdDsOfdmChanEntry 4}

cerRpdDsOfdmChanRpdDepiChanId OBJECT-TYPE
    SYNTAX Unsigned32 (0..255)
    MAX-ACCESS   read-only
    STATUS current
    DESCRIPTION
        "DEPI channel ID associated with this RPD channel selector.
         Zero means that this channel selector channel type does not
         use a DEPI channel ID."
    REFERENCE
        "DEPI Figure 7-24 and Table 7-7"
    ::= { cerRpdDsOfdmChanEntry 5}

cerRpdDsOfdmChanDataPwId OBJECT-TYPE
    SYNTAX          Unsigned32 (1..4294967295)
    MAX-ACCESS      read-only
    STATUS          current
    DESCRIPTION
        "The Core ID of the data Pseudo-wire carrying the OFDM channel." 
    ::= { cerRpdDsOfdmChanEntry 6 }

cerRpdDsOfdmChanRpdPlcChanSelector OBJECT-TYPE
    SYNTAX Unsigned32
    MAX-ACCESS   read-only
    STATUS current
    DESCRIPTION
        "DEPI channel selector for the PLC of this OFDM channel on the RPD. This 
         24 bit number has the RPD RF port number in the upper 8 bits, the channel 
         type in the middle 8 bits, and the channel ID in low 8 bits."
    REFERENCE
        "DEPI Table 9"
    ::= { cerRpdDsOfdmChanEntry 7 }

--========================= cerRpdUsChanTable =========================

cerRpdUsChanTable OBJECT-TYPE
    SYNTAX      SEQUENCE OF CerRpdUsChanEntry
    MAX-ACCESS  not-accessible
    STATUS      current
    DESCRIPTION
        "This status table contains the US SC-QAM and OFDMA PHY channels on an RPD."
    ::= { cerRphyMib 17 }

cerRpdUsChanEntry OBJECT-TYPE
    SYNTAX      CerRpdUsChanEntry
    MAX-ACCESS  not-accessible
    STATUS      current
    DESCRIPTION
        "An entry contains one RPD US channel."
    INDEX { cerRpdUsChanRpdIndex, cerRpdUsChanRpdChanIfIndex }
    ::= { cerRpdUsChanTable 1 }

CerRpdUsChanEntry ::= SEQUENCE {
    cerRpdUsChanRpdIndex                CerRpdIndex,
    cerRpdUsChanRpdChanIfIndex          InterfaceIndex,
    cerRpdUsChanCoreChanIfIndex         InterfaceIndex,
    cerRpdUsChanRpdChanSelector         Unsigned32,
    cerRpdUsChanDataPwId                Unsigned32
    }

cerRpdUsChanRpdIndex OBJECT-TYPE
    SYNTAX CerRpdIndex
    MAX-ACCESS not-accessible
    STATUS current
    DESCRIPTION
        "The index of the RPD."
    ::= { cerRpdUsChanEntry 1}

cerRpdUsChanRpdChanIfIndex OBJECT-TYPE
    SYNTAX     InterfaceIndex
    MAX-ACCESS not-accessible
    STATUS     current
    DESCRIPTION
        "The PHY channel ifIndex of this US channel."
    ::= { cerRpdUsChanEntry 2 }

cerRpdUsChanCoreChanIfIndex OBJECT-TYPE
    SYNTAX      InterfaceIndex
    MAX-ACCESS  read-only
    STATUS      current
    DESCRIPTION
        "The MAC channel ifIndex for US channel."
    ::= { cerRpdUsChanEntry 3 }

cerRpdUsChanRpdChanSelector OBJECT-TYPE
    SYNTAX Unsigned32
    MAX-ACCESS   read-only
    STATUS current
    DESCRIPTION
        "DEPI channel selector for this US channel on the RPD. This 24 bit number
         has the RPD RF port number in the upper 8 bits, the channel type in
         the middle 8 bits, and the channel ID in low 8 bits."
    REFERENCE
        "DEPI Table 9"
    ::= { cerRpdUsChanEntry 4}

cerRpdUsChanDataPwId OBJECT-TYPE
    SYNTAX          Unsigned32 (1..4294967295)
    MAX-ACCESS      read-only
    STATUS          current
    DESCRIPTION
        "The Core ID of the data Pseudo-wire carrying the US channel." 
    ::= { cerRpdUsChanEntry 5 }


--========================= cerCoreChanToRpdChanTable =========================

cerCoreChanToRpdChanTable OBJECT-TYPE
    SYNTAX      SEQUENCE OF CerCoreChanToRpdChanEntry
    MAX-ACCESS  not-accessible
    STATUS      current
    DESCRIPTION
        "This status table contains the mapping of MAC channels to RPHY channels."
    ::= { cerRphyMib 18 }

cerCoreChanToRpdChanEntry OBJECT-TYPE
    SYNTAX      CerCoreChanToRpdChanEntry
    MAX-ACCESS  not-accessible
    STATUS      current
    DESCRIPTION
        "An entry contains one MAC channel,PHY channel pair."
    INDEX { cerCoreChanToRpdChanCoreIfIndex, cerCoreChanToRpdChanRpdIndex, cerCoreChanToRpdChanRpdRfPort }
    ::= { cerCoreChanToRpdChanTable 1 }

CerCoreChanToRpdChanEntry ::= SEQUENCE {
    cerCoreChanToRpdChanCoreIfIndex         InterfaceIndex,
    cerCoreChanToRpdChanRpdIndex            CerRpdIndex,
    cerCoreChanToRpdChanRpdRfPort           Unsigned32,
    cerCoreChanToRpdChanRpdIfIndex          InterfaceIndex,
    cerCoreChanToRpdChanDirection           INTEGER
}

cerCoreChanToRpdChanCoreIfIndex OBJECT-TYPE
    SYNTAX      InterfaceIndex
    MAX-ACCESS  not-accessible
    STATUS      current
    DESCRIPTION
        "The ifIndex of the MAC channel for this PHY channel."
    ::= { cerCoreChanToRpdChanEntry 1 }

cerCoreChanToRpdChanRpdIndex OBJECT-TYPE
    SYNTAX CerRpdIndex
    MAX-ACCESS not-accessible
    STATUS     current
    DESCRIPTION
        "The RPD Index for this PHY channel."
    ::= { cerCoreChanToRpdChanEntry 2 }

cerCoreChanToRpdChanRpdRfPort OBJECT-TYPE
    SYNTAX Unsigned32 (1..4)
    MAX-ACCESS not-accessible
    STATUS     current
    DESCRIPTION
        "The RF port number of the RPD RF port for this PHY channel."
    ::= { cerCoreChanToRpdChanEntry 3 }

cerCoreChanToRpdChanRpdIfIndex OBJECT-TYPE
    SYNTAX      InterfaceIndex
    MAX-ACCESS  read-only
    STATUS      current
    DESCRIPTION
        "The PHY channel ifIndex of the RPHY channel."
    ::= { cerCoreChanToRpdChanEntry 4 }

cerCoreChanToRpdChanDirection OBJECT-TYPE
    SYNTAX INTEGER {
        upstream(1),
        downstream(2)
    }
    MAX-ACCESS read-only
    STATUS     current
    DESCRIPTION
        "The direction of the channel."
    ::= { cerCoreChanToRpdChanEntry 5 }

--========================= cerRpdToCoreChanTable =========================

cerRpdToCoreChanTable OBJECT-TYPE
    SYNTAX      SEQUENCE OF CerRpdToCoreChanEntry
    MAX-ACCESS  not-accessible
    STATUS      current
    DESCRIPTION
        "This status table contains the mapping of RPDs to MAC channels."
    ::= { cerRphyMib 19 }

cerRpdToCoreChanEntry OBJECT-TYPE
    SYNTAX      CerRpdToCoreChanEntry
    MAX-ACCESS  not-accessible
    STATUS      current
    DESCRIPTION
        "An entry contains one PHY channel,MAC channel pair."
    INDEX { cerRpdToCoreChanRpdIndex, cerRpdToCoreChanRpdRfPort, cerRpdToCoreChanRpdIfIndex }
    ::= { cerRpdToCoreChanTable 1 }

CerRpdToCoreChanEntry ::= SEQUENCE {
    cerRpdToCoreChanRpdIndex            CerRpdIndex,
    cerRpdToCoreChanRpdIfIndex          InterfaceIndex,
    cerRpdToCoreChanCoreIfIndex         InterfaceIndex,
    cerRpdToCoreChanRpdRfPort           Unsigned32,
    cerRpdToCoreChanDirection           INTEGER
}

cerRpdToCoreChanRpdIndex OBJECT-TYPE
    SYNTAX CerRpdIndex
    MAX-ACCESS not-accessible
    STATUS     current
    DESCRIPTION
        "The RPD Index for this PHY channel."
    ::= { cerRpdToCoreChanEntry 1 }

cerRpdToCoreChanRpdIfIndex OBJECT-TYPE
    SYNTAX      InterfaceIndex
    MAX-ACCESS  not-accessible
    STATUS      current
    DESCRIPTION
        "The PHY channel ifIndex."
    ::= { cerRpdToCoreChanEntry 2 }

cerRpdToCoreChanCoreIfIndex OBJECT-TYPE
    SYNTAX      InterfaceIndex
    MAX-ACCESS  read-only
    STATUS      current
    DESCRIPTION
        "The ifIndex of the MAC channel for this PHY channel."
    ::= { cerRpdToCoreChanEntry 3 }

cerRpdToCoreChanRpdRfPort OBJECT-TYPE
    SYNTAX Unsigned32 (1..4)
    MAX-ACCESS not-accessible
    STATUS     current
    DESCRIPTION
        "The RF port number of the RPD RF port for this PHY channel."
    ::= { cerRpdToCoreChanEntry 4 }

cerRpdToCoreChanDirection OBJECT-TYPE
    SYNTAX INTEGER {
        upstream(1),
        downstream(2)
    }
    MAX-ACCESS read-only
    STATUS     current
    DESCRIPTION
        "The direction of the channel."
    ::= { cerRpdToCoreChanEntry 5 }

--========================= cerRphyDscpTable =========================

cerRphyDscpTable OBJECT-TYPE
    SYNTAX      SEQUENCE OF CerRphyDscpEntry
    MAX-ACCESS  not-accessible
    STATUS      current
    DESCRIPTION
        "This status table contains the DSCP value for different
         traffic types."
    ::= { cerRphyMib 20 }

cerRphyDscpEntry OBJECT-TYPE
    SYNTAX      CerRphyDscpEntry
    MAX-ACCESS  not-accessible
    STATUS      current
    DESCRIPTION
        "An entry contains one traffic priority."
    INDEX { cerRphyDscpPktType }
    ::= { cerRphyDscpTable 1 }

CerRphyDscpEntry ::= SEQUENCE {
        cerRphyDscpPktType     INTEGER,
        cerRphyDscpValue       Unsigned32
    }

cerRphyDscpPktType OBJECT-TYPE
    SYNTAX INTEGER {
        rpdCntl(1),
        mapUcds(2),
        dsDataPws(3),
        usBwReqPws(4),
        usDataPws(5),
        ptp(6),
        ndr(7),
        video(8),
        broadcast(9)
    }
    MAX-ACCESS not-accessible
    STATUS     current
    DESCRIPTION
        "The session traffic type:
             rpdCntl: L2TPv3, BDCP and GCP Control messages
             mapUcds: MAP/UCD messages in either direction
             dsDataPws: Downstream, non-MAP/UCD data flows
             usBwReqPws: Upstream bandwidth request PWs
             usDataPws: Upstream non-bandwidth request data PWs
             ptp: PTP packets
             ndr: NDR upstream OOB static PWs
             video: Video packets
             broadcast: Broadcast packets."
    ::= { cerRphyDscpEntry 1 }

cerRphyDscpValue OBJECT-TYPE
    SYNTAX Unsigned32 (0..63)
    MAX-ACCESS read-write
    STATUS     current
    DESCRIPTION
        "The 6-bit IPv4 DSCP or IPv6 TOS value to use for
         RPHY data packets. The default for the data priorities
         is zero (best effort). The default for PTP packets is 47
         (Special Expedited Forwarding).  The default for the 
         other 2 is 46 (Expedited Forwarding). The default for video
         and broadcast is 34."
    ::= { cerRphyDscpEntry 2 }


--
-- RPD ifTable
--
 
cerRpdIfTable OBJECT-TYPE
    SYNTAX      SEQUENCE OF CerRpdIfEntry
    MAX-ACCESS  not-accessible
    STATUS      current
    DESCRIPTION
            "A list of interface entries on an RPD."
    ::= { cerRphyMib 21 }

cerRpdIfEntry OBJECT-TYPE
    SYNTAX      CerRpdIfEntry
    MAX-ACCESS  not-accessible
    STATUS      current
    DESCRIPTION
            "An entry containing management information applicable to a
            particular interface on an RPD."
    INDEX   { cerRpdIfIndex }
    ::= { cerRpdIfTable 1 }

CerRpdIfEntry ::=
    SEQUENCE {
        cerRpdIfIndex                 InterfaceIndex,
        cerRpdIfRpdIndex              CerRpdIndex,
        cerRpdIfRfPortId              Unsigned32, 
        cerRpdIfType                  IANAifType,
        cerRpdIfMtu                   Integer32,
        cerRpdIfOperStatus            INTEGER,
        cerRpdIfLastChange            TimeTicks,
        cerRpdIfDiscards              Counter64,
        cerRpdIfErrors                Counter64,
        cerRpdIfCounterDiscontinuityTime  TimeStamp 
    }

cerRpdIfIndex OBJECT-TYPE
    SYNTAX      InterfaceIndex
    MAX-ACCESS  not-accessible
    STATUS      current
    DESCRIPTION
            "A unique value, greater than zero, for each interface.  It
            is recommended that values are assigned contiguously
            starting from 1.  The value for each interface sub-layer
            must remain constant at least from one re-initialization of
            the entitys network management system to the next re-initialization."
    ::= { cerRpdIfEntry 1 }

cerRpdIfRpdIndex OBJECT-TYPE
    SYNTAX CerRpdIndex
    MAX-ACCESS read-only
    STATUS current
    DESCRIPTION
        "The index of the RPD."
    ::= { cerRpdIfEntry 2 }

cerRpdIfRfPortId  OBJECT-TYPE
    SYNTAX Unsigned32 (1..4) 
    MAX-ACCESS read-only
    STATUS current
    DESCRIPTION
        "Index of RF port on the RPD for this interface."
    ::= { cerRpdIfEntry 3}

cerRpdIfType OBJECT-TYPE
    SYNTAX      IANAifType
    MAX-ACCESS  read-only
    STATUS      current
    DESCRIPTION
            "The type of interface.  Additional values for ifType are
            assigned by the Internet Assigned Numbers Authority (IANA),
            through updating the syntax of the IANAifType textual
            convention."
    ::= { cerRpdIfEntry 4 }

cerRpdIfMtu OBJECT-TYPE
    SYNTAX      Integer32
    MAX-ACCESS  read-only
    STATUS      current
    DESCRIPTION
            "The size of the largest packet which can be sent/received
            on the interface, specified in octets.  For interfaces that
            are used for transmitting network datagrams, this is the
            size of the largest network datagram that can be sent on the
            interface."
    ::= { cerRpdIfEntry 5 }

cerRpdIfOperStatus OBJECT-TYPE
    SYNTAX  INTEGER {
                up(1),        -- ready to pass packets
                down(2),
                testing(3),   -- in some test mode
                unknown(4),   -- status can not be determined
                              -- for some reason.
                dormant(5),
                notPresent(6),    -- some component is missing
                lowerLayerDown(7) -- down due to state of
                                  -- lower-layer interface(s)
            }
    MAX-ACCESS  read-only
    STATUS      current
    DESCRIPTION
            "The current operational state of the interface.  The
            testing(3) state indicates that no operational packets can
            be passed. CerRpdIfOperStatus should change to up(1) if the interface 
            is ready to transmit and receive network traffic; it should
            change to dormant(5) if the interface is waiting for
            external actions (such as a serial line waiting for an
            incoming connection); it should remain in the down(2) state
            if and only if there is a fault that prevents it from going
            to the up(1) state; it should remain in the notPresent(6)
            state if the interface has missing (typically, hardware)
            components or channel configuration to the RPD has not occurred
            or has failed.
                        Values definitions are as follows:
            'up'         
                indicates that the PHY channel is ready to pass packets.
            'down' 
                indicates that PHY channel has been successfully
                configured, but is not usable, either because it is admin down or
                because some dependency has not been met (e.g., the cable mac is OOS), 
                or indications available at the service level indicate 
                that the PHY channel is not passing packets.
            'testing' 
                not used to test.
            'unknown'
                Status cannot be determined for some reason
            'dormant' 
                indicates that the PHY channel is not in a condition to 
                pass packets but is in a 'pending' state, waiting for 
                some external event.
            'notPresent' 
                indicates that some component is missing to accomplish 
                the setup of the PHY channel.  It can be a configuration 
                error, incomplete configuration, or a missing H/W 
                component.
            'lowerLayerDown' 
                indicates one or more of the lower-layer 
                interfaces responsible for running the PHY channel
                is not in OperStatus 'up' state."
    DEFVAL { notPresent }
    ::= { cerRpdIfEntry 6 }

cerRpdIfLastChange OBJECT-TYPE
    SYNTAX      TimeTicks
    MAX-ACCESS  read-only
    STATUS      current
    DESCRIPTION
            "The value of RPD sysUpTime at the time the interface entered
            its current operational state.  If the current state was
            entered prior to the last re-initialization of the local
            network management subsystem, then this object contains a
            zero value."
    ::= { cerRpdIfEntry 7 }

cerRpdIfDiscards OBJECT-TYPE
    SYNTAX      Counter64
    MAX-ACCESS  read-only
    STATUS      current
    DESCRIPTION
            "The total number of unerrored frames discarded on this interface.

            Discontinuities in the value of this counter can occur at
            re-initialization of the management system, and at other
            times as indicated by the value of
            cerRpdIfCounterDiscontinuityTime."
    ::= { cerRpdIfEntry 8 }

cerRpdIfErrors OBJECT-TYPE
    SYNTAX      Counter64
    MAX-ACCESS  read-only
    STATUS      current
    DESCRIPTION
            "The total number of errored frames on this interface.

            Discontinuities in the value of this counter can occur at
            re-initialization of the management system, and at other
            times as indicated by the value of
            cerRpdIfCounterDiscontinuityTime."
    ::= { cerRpdIfEntry 9 }

cerRpdIfCounterDiscontinuityTime OBJECT-TYPE
    SYNTAX      TimeStamp
    MAX-ACCESS  read-only
    STATUS      current
    DESCRIPTION
            "The value of Rpd sysUpTime on the most recent occasion at which
            any one or more of this interfaces counters suffered a
            discontinuity.  The relevant counters are the specific
            instances associated with this interface of any Counter32 or
            Counter64 object contained in the cerRpdIfTable or cerRpdIfXTable.  If
            no such discontinuities have occurred since the last re-initialization 
            of the local management subsystem, then this object contains a zero value."
    ::= { cerRpdIfEntry 10 }

--
-- RPD DS Statistics Table
--
 
cerRpdDsStatsTable  OBJECT-TYPE
    SYNTAX      SEQUENCE OF CerRpdDsStatsEntry
    MAX-ACCESS  not-accessible
    STATUS      current
    DESCRIPTION
            "A list of DS channels on an RPD."
    ::= { cerRphyMib 22 }

cerRpdDsStatsEntry OBJECT-TYPE
    SYNTAX      CerRpdDsStatsEntry
    MAX-ACCESS  not-accessible
    STATUS      current
    DESCRIPTION
            "An entry containing RPD DS channel statistics."
    INDEX   { cerRpdDsStatsIfIndex }
    ::= { cerRpdDsStatsTable 1 }

CerRpdDsStatsEntry ::=
    SEQUENCE {
        cerRpdDsStatsIfIndex               InterfaceIndex,
        cerRpdDsStatsRpdIndex              CerRpdIndex, 
        cerRpdDsStatsRfPortId              Unsigned32, 
        cerRpdDsStatsPktsOut               Counter64
    }

cerRpdDsStatsIfIndex OBJECT-TYPE
    SYNTAX      InterfaceIndex
    MAX-ACCESS  not-accessible
    STATUS      current
    DESCRIPTION
            "A unique value, greater than zero, for each interface.  It
            is recommended that values are assigned contiguously
            starting from 1.  The value for each interface sub-layer
            must remain constant at least from one re-initialization of
            the entity's network management system to the next re-
            initialization."
    ::= { cerRpdDsStatsEntry 1 }

cerRpdDsStatsRpdIndex OBJECT-TYPE
    SYNTAX CerRpdIndex
    MAX-ACCESS read-only
    STATUS current
    DESCRIPTION
        "Global index for this RPD."
    ::= { cerRpdDsStatsEntry 2 }

cerRpdDsStatsRfPortId OBJECT-TYPE
    SYNTAX Unsigned32 (1..4)
    MAX-ACCESS read-only
    STATUS current
    DESCRIPTION
        "Index of DS RF port on the RPD."
    ::= { cerRpdDsStatsEntry 3 }

cerRpdDsStatsPktsOut OBJECT-TYPE
    SYNTAX      Counter64
    MAX-ACCESS  read-only
    STATUS      current
    DESCRIPTION
            "The total number of packets transmitted on this DS channel."
    ::= { cerRpdDsStatsEntry 4 }

--
-- RPD Data Table
--

cerRpdDataTable OBJECT-TYPE
    SYNTAX  SEQUENCE OF CerRpdDataEntry
    MAX-ACCESS not-accessible
    STATUS  current
    DESCRIPTION
        "This table contains status information for the RPDs."
    ::= { cerRphyMib 23 }

cerRpdDataEntry OBJECT-TYPE
    SYNTAX  CerRpdDataEntry
    MAX-ACCESS not-accessible
    STATUS  current
    DESCRIPTION
        "A conceptual row containing status information about one RPD."
    INDEX { cerRpdDataRpdIndex }
    ::= { cerRpdDataTable 1 }
    
CerRpdDataEntry ::= SEQUENCE {
        cerRpdDataRpdIndex            CerRpdIndex,
        cerRpdDataIpAddrType          InetAddressType,
        cerRpdDataIpAddr              InetAddressIPv4or6,
        cerRpdDataSysUpTime           TimeStamp,
        cerRpdDataNumDsPorts          Integer32,
        cerRpdDataNumUsPorts          Integer32,
        cerRpdDataPrState             PrimaryState,
        cerRpdDataSecState            SecondaryState,
        cerRpdDataSerialNum           SnmpAdminString,
        cerRpdDataVendorName          SnmpAdminString,
        cerRpdDataVendorOid           Unsigned32,
        cerRpdDataModelNumber         SnmpAdminString,
        cerRpdDataMacAddr             MacAddress,
        cerRpdDataBootVersion         SnmpAdminString,
        cerRpdDataSsdStatus           INTEGER,
        cerRpdDataHwVersion           SnmpAdminString,
        cerRpdDataSwVersion           SnmpAdminString,
        cerRpdDataDeviceDescription   SnmpAdminString,
        cerRpdDataAssetId             SnmpAdminString,
        cerRpdDataLastResetReason     DisplayString,
        cerRpdDataDevIdUsBurstRcvrVendorId   Unsigned32,
        cerRpdDataDevIdUsBurstRcvrModelNum   SnmpAdminString,
        cerRpdDataDevIdUsBurstRcvrDrivVer    SnmpAdminString,
        cerRpdDataDevIdUsBurstRcvrSerialNum  SnmpAdminString,
        cerRpdDataGcpProtocolVersion         SnmpAdminString,
        cerRpdDataGcpSchemaVersion           SnmpAdminString,
        cerRpdDataLocationDescription        SnmpAdminString,
        cerRpdDataLocationLatitude           SnmpAdminString,
        cerRpdDataLocationLongitude          SnmpAdminString,
        cerRpdDataCurrentSwImageLastUpdate   DateAndTime,
        cerRpdDataCurrentSwImageName         SnmpAdminString,
        cerRpdDataCurrentSwImageServerType   InetAddressType,
        cerRpdDataCurrentSwImageServerAddress InetAddress,
        cerRpdDataSsdAttempts                Counter32,
        cerRpdDataSsdTargetImageName         SnmpAdminString,
        cerRpdDataNumCrashFiles              Unsigned32,
        cerRpdDataLastStatusReadTime         TimeStamp,
        cerRpdDataDeviceAlias                SnmpAdminString,
        cerRpdDataInitState                  INTEGER,
        cerRpdDataShelfSerialNumber          SnmpAdminString,
        cerRpdDataSupportsAdp                TruthValue,
        cerRpdDataAdpNonOptimal              TruthValue,
        cerRpdDataAdpSavedPreferredPort      INTEGER,
        cerRpdDataAdpForward                 TruthValue,
        cerRpdDataPnmCapabSupportedPnmTests			BITS,
		cerRpdDataPnmCapabUtscNumSacs				Unsigned32,
		cerRpdDataPnmCapabUpcMinNumSymbols25Khz		Unsigned32,
		cerRpdDataPnmCapabUpcMaxNumSymbols25Khz		Unsigned32,
		cerRpdDataPnmCapabUpcMinNumSymbols50Khz		Unsigned32,
		cerRpdDataPnmCapabUpcMaxNumSymbols50Khz		Unsigned32,
		cerRpdDataPnmCapabUpcSupportsStaggeredPies	TruthValue,
		cerRpdDatadPnmCapabUpcSupportsDedicatedPwUpcRxMer		TruthValue,
		cerRpdDataPnmCapabUpcSupportsFreqDomainSamples			TruthValue
               
    }

cerRpdDataRpdIndex OBJECT-TYPE
    SYNTAX          CerRpdIndex
    MAX-ACCESS      not-accessible
    STATUS          current
    DESCRIPTION
        "The RPD Index." 
    ::= { cerRpdDataEntry 1 }

cerRpdDataIpAddrType OBJECT-TYPE
    SYNTAX InetAddressType
    MAX-ACCESS   read-only
    STATUS current
    DESCRIPTION
        "Type of the RPD IP address; only IPv4 or IPv6 are allowed."
    DEFVAL { ipv6 }
    ::= { cerRpdDataEntry 2 }

cerRpdDataIpAddr OBJECT-TYPE
    SYNTAX InetAddressIPv4or6
    MAX-ACCESS read-only
    STATUS current
    DESCRIPTION
        "The IP address of this RPD."
    DEFVAL { "" }
    ::= { cerRpdDataEntry 3 }

cerRpdDataSysUpTime OBJECT-TYPE
    SYNTAX      TimeStamp
    MAX-ACCESS  read-only
    STATUS      current
    DESCRIPTION 
        "This attribute is the time (in hundredths of a second) 
         since the RPD was last re-initialized. This value is 
         not reported by the RPD; it is the Core value of sysUpTime."
    ::= { cerRpdDataEntry 4 }

cerRpdDataNumDsPorts OBJECT-TYPE
    SYNTAX      Integer32 (1..4)
    MAX-ACCESS  read-only
    STATUS      current
    DESCRIPTION
        "Number of DS RF ports this RPD contains."
    DEFVAL { 1 }
    ::= { cerRpdDataEntry 5 }

cerRpdDataNumUsPorts OBJECT-TYPE
    SYNTAX      Integer32 (1..4)
    MAX-ACCESS  read-only
    STATUS      current
    DESCRIPTION
        "Number of US RF ports this RPD contains."
    DEFVAL { 1 }
    ::= { cerRpdDataEntry 6 }

cerRpdDataPrState OBJECT-TYPE
    SYNTAX      PrimaryState
    MAX-ACCESS  read-only
    STATUS      current
    DESCRIPTION
        " This is the primary state of this card. "
    ::= { cerRpdDataEntry 7 }

cerRpdDataSecState OBJECT-TYPE
    SYNTAX      SecondaryState
    MAX-ACCESS  read-only
    STATUS      current
    DESCRIPTION
        " This is the secondary state of this card. "
    ::= { cerRpdDataEntry 8 }

cerRpdDataSerialNum OBJECT-TYPE
    SYNTAX      SnmpAdminString (SIZE(0..32))
    MAX-ACCESS  read-only
    STATUS      current
    DESCRIPTION
        " This is the serial number of the card. "
    DEFVAL { "" }
    ::= { cerRpdDataEntry 9 }

cerRpdDataVendorName OBJECT-TYPE
    SYNTAX      SnmpAdminString (SIZE(0..255))
    MAX-ACCESS  read-only
    STATUS      current
    DESCRIPTION
        " Name of the product (FRU). "
    DEFVAL { "ARRIS" }
    ::= { cerRpdDataEntry 10 }

cerRpdDataVendorOid OBJECT-TYPE
    SYNTAX Unsigned32 (0..65535)
    MAX-ACCESS  read-only
    STATUS      current
    DESCRIPTION
        " OID of the RPD vendor (e.g., Arris Interactive LLC). Populated using TLV 50.19.2"
    REFERENCE
        "https://www.iana.org/assignments/enterprise-numbers/enterprise-numbers"
    DEFVAL { 4115 }
    ::= { cerRpdDataEntry 11 }

cerRpdDataModelNumber OBJECT-TYPE
    SYNTAX      SnmpAdminString (SIZE(0..255))
    MAX-ACCESS  read-only
    STATUS      current
    DESCRIPTION
        " Name of the model of this product (FRU). "
    DEFVAL { "" }
    ::= { cerRpdDataEntry 12 }

cerRpdDataMacAddr OBJECT-TYPE
    SYNTAX       MacAddress
    MAX-ACCESS   read-only
    STATUS       current
    DESCRIPTION
        "RPD MAC address. Zeros if not reported."
    ::= { cerRpdDataEntry 13 }

cerRpdDataBootVersion OBJECT-TYPE
    SYNTAX SnmpAdminString (SIZE(0..90))
    MAX-ACCESS read-only
    STATUS current
    DESCRIPTION
        " The current versions of the boot loaders installed on the card. "
    DEFVAL { "" }
    ::= { cerRpdDataEntry 14 }

cerRpdDataSsdStatus OBJECT-TYPE
    SYNTAX INTEGER {
        other(1),
        idle(2),
        inProgress(3),
        cvcVerified(4),
        cvcRejected(5),
        cdeFileVerified(6),
        codeFileRejected(7)
    }
    MAX-ACCESS read-only
    STATUS      current
    DESCRIPTION
        "The RPD status of the software file update.  This is populated using TLV 90.4"
    ::= { cerRpdDataEntry 15 }

cerRpdDataHwVersion OBJECT-TYPE
    SYNTAX      SnmpAdminString (SIZE(0..128))
    MAX-ACCESS  read-only
    STATUS      current
    DESCRIPTION
        " This is the hardware version of the card. "
    DEFVAL { "" }
    ::= { cerRpdDataEntry 16 }

cerRpdDataSwVersion OBJECT-TYPE
    SYNTAX      SnmpAdminString (SIZE(0..128))
    MAX-ACCESS  read-only
    STATUS      current
    DESCRIPTION
        " This is the software version of the card. "
    DEFVAL { "" }
    ::= { cerRpdDataEntry 17 }

cerRpdDataDeviceDescription OBJECT-TYPE
    SYNTAX      SnmpAdminString
    MAX-ACCESS  read-only
    STATUS      current
    DESCRIPTION
        "A description of the RPD. Populated using TLV 50.19.7."
    DEFVAL { "" }
    ::= { cerRpdDataEntry 18 }

cerRpdDataAssetId OBJECT-TYPE
    SYNTAX      SnmpAdminString (SIZE(0..32))
    MAX-ACCESS  read-only
    STATUS      current
    DESCRIPTION
        "The AssetId is used to communicate the asset tracking identifier
         as assigned by a network manager, Populated using TLV 50.19.17."
    DEFVAL { "" }
    ::= { cerRpdDataEntry 19 }

cerRpdDataLastResetReason OBJECT-TYPE
    SYNTAX      DisplayString (SIZE(0..64))
    MAX-ACCESS  read-only
    STATUS      current
    DESCRIPTION
        "The reason for the latest card recovery. "
    DEFVAL { "" }
    ::= { cerRpdDataEntry 21 }

cerRpdDataDevIdUsBurstRcvrVendorId OBJECT-TYPE
    SYNTAX      Unsigned32 (0..65535)
    MAX-ACCESS  read-only 
    STATUS      current 
    DESCRIPTION 
        "This attribute reports the IANA-assigned SMI Network 
         Management Private Enterprise Code of the RPD's US burst 
         receiver manufacturer, as specified in RFC 5612.
         Populated using TLV 50.19.10."
    DEFVAL { 0 }
    ::= { cerRpdDataEntry 23 }
        
cerRpdDataDevIdUsBurstRcvrModelNum OBJECT-TYPE
    SYNTAX      SnmpAdminString (SIZE(3..16))
    MAX-ACCESS  read-only 
    STATUS      current 
    DESCRIPTION 
        "This attribute reports the model number used by the vendor 
         to identify the RPD's US burst receiver. The format is 
         vendor proprietary. Populated using TLV 50.19.11."
    DEFVAL { "" }
    ::= { cerRpdDataEntry 24 }
        
cerRpdDataDevIdUsBurstRcvrDrivVer OBJECT-TYPE
    SYNTAX      SnmpAdminString (SIZE(3..16))
    MAX-ACCESS  read-only 
    STATUS      current 
    DESCRIPTION 
        "This attribute reports the driver version of the RPD's 
         US burst receiver. The format is vendor proprietary.
         Populated using TLV 50.19.12."
    DEFVAL { "" }
    ::= { cerRpdDataEntry 25 }
    
cerRpdDataDevIdUsBurstRcvrSerialNum OBJECT-TYPE
    SYNTAX      SnmpAdminString (SIZE(5..16))
    MAX-ACCESS  read-only 
    STATUS      current 
    DESCRIPTION 
        "This attribute reports the serial number of the RPD's 
         US burst receiver. The format is vendor proprietary.
         Populated using TLV 50.19.13."
    DEFVAL { "" }
    ::= { cerRpdDataEntry 26 }

cerRpdDataGcpProtocolVersion OBJECT-TYPE
    SYNTAX      SnmpAdminString (SIZE(3..32))
    MAX-ACCESS  read-only
    STATUS      current
    DESCRIPTION
        " This is the RCP protocol supported by the RPD. "
    DEFVAL { "1.0" }
    ::= { cerRpdDataEntry 27 }

cerRpdDataGcpSchemaVersion OBJECT-TYPE
    SYNTAX      SnmpAdminString (SIZE(5..32))
    MAX-ACCESS  read-only
    STATUS      current
    DESCRIPTION
        " This is the RCP schema supported by the RPD."
    DEFVAL { "1.0.1" }
    ::= { cerRpdDataEntry 28 }

cerRpdDataLocationDescription OBJECT-TYPE
    SYNTAX      SnmpAdminString (SIZE(0..255))
    MAX-ACCESS  read-only
    STATUS      current
    DESCRIPTION
        " This is the RPD Location Description. Populated using TLV 50.24.1."
    DEFVAL { "" }
    ::= { cerRpdDataEntry 29 }

cerRpdDataLocationLatitude OBJECT-TYPE
    SYNTAX      SnmpAdminString (SIZE(9))
    MAX-ACCESS  read-only
    STATUS      current
    DESCRIPTION
        " This is the Location Latitude. Populated using TLV 50.24.2."
    ::= { cerRpdDataEntry 30 } 

cerRpdDataLocationLongitude OBJECT-TYPE
    SYNTAX      SnmpAdminString (SIZE(10))
    MAX-ACCESS  read-only
    STATUS      current
    DESCRIPTION
        " This is the Location Longitude. Populated using TLV 50.24.3."
    ::= { cerRpdDataEntry 31 }

cerRpdDataCurrentSwImageLastUpdate OBJECT-TYPE
    SYNTAX      DateAndTime
    MAX-ACCESS  read-only
    STATUS      current
    DESCRIPTION
        "This attribute reports the most recent date and time the 
         software image currently running on the RPD was updated.
         Populated using TLV 50.19.19."
    ::= { cerRpdDataEntry 32 }

cerRpdDataCurrentSwImageName OBJECT-TYPE
    SYNTAX      SnmpAdminString
    MAX-ACCESS  read-only
    STATUS      current
    DESCRIPTION
        "This attribute reports the name of the software image currently 
         running on the RPD. Populated using TLV 50.19.20."
    DEFVAL { "" }
    ::= { cerRpdDataEntry 33 }

cerRpdDataCurrentSwImageServerType OBJECT-TYPE
    SYNTAX      InetAddressType
    MAX-ACCESS  read-only
    STATUS      current
    DESCRIPTION
        "This attribute reports the server internet address type 
         of the software image currently running on the RPD."
    DEFVAL { ipv6 }        
    ::= { cerRpdDataEntry 34 }

cerRpdDataCurrentSwImageServerAddress OBJECT-TYPE
    SYNTAX      InetAddress
    MAX-ACCESS  read-only
    STATUS      current
    DESCRIPTION
        " This attribute reports the Internet address of the server from which 
         the software image currently running on the RPD was downloaded. 
         Populated using TLV 50.19.21."
    ::= { cerRpdDataEntry 35 }

cerRpdDataSsdAttempts OBJECT-TYPE
    SYNTAX          Counter32
    MAX-ACCESS      read-only
    STATUS          current
    DESCRIPTION
        "The number of attempts to initiate SSD of the cerRpdDataSsdTargetImageName." 
    ::= { cerRpdDataEntry 36 }

cerRpdDataSsdTargetImageName OBJECT-TYPE
    SYNTAX      SnmpAdminString (SIZE(0..255))
    MAX-ACCESS  read-only
    STATUS      current
    DESCRIPTION
        " This is the target image name of the RPD after successful SSD."
    DEFVAL { "" }
    ::= { cerRpdDataEntry 37 }

cerRpdDataNumCrashFiles OBJECT-TYPE
    SYNTAX      Unsigned32
    MAX-ACCESS  read-only
    STATUS      current
    DESCRIPTION
        " This is the number of crash files currently on the RPD,
          and is populated using TLV 100.1.2."
    ::= { cerRpdDataEntry 38 }

cerRpdDataLastStatusReadTime OBJECT-TYPE
    SYNTAX      TimeStamp
    MAX-ACCESS  read-only
    STATUS      current
    DESCRIPTION 
        "This attribute is the time (in hundredths of a second) 
        when the status finished being completely read from the RPD. 
        Status includes all counts and various environmental values 
        (temp, voltage,and current). It does not include unchanging 
        values like serial number that are read once when the RPD 
        initializes.Zero means that the status has not yet been 
        completely read."
    DEFVAL { 0 }
    ::= { cerRpdDataEntry 39 }

cerRpdDataDeviceAlias OBJECT-TYPE
    SYNTAX      SnmpAdminString
    MAX-ACCESS  read-only 
    STATUS      current 
    DESCRIPTION 
        "This attribute reports the device name assigned by the 
        operator and represents a 'handle' for the RPD.
        Populated using TLV 50.19.8."
    DEFVAL { "" }
    ::= { cerRpdDataEntry 40 }

cerRpdDataInitState OBJECT-TYPE
    SYNTAX      INTEGER {
        notConnected(1),
        gcpConnected(2),
        waitingForPtpSync(3),
        ptpSyncDuringInit(4),
        initialized(5)
    }
    MAX-ACCESS  read-only 
    STATUS      current 
    DESCRIPTION 
        "This attribute reports the RPD state as it initializes 
         and before it is configured."
    DEFVAL { notConnected }
    ::= { cerRpdDataEntry 41 }

cerRpdDataShelfSerialNumber OBJECT-TYPE
        SYNTAX     SnmpAdminString
        MAX-ACCESS read-only
        STATUS     current
        DESCRIPTION
            "The serial number returned by the RPD in TLV 100.6.11 for 
             Class equal chassis(3) in TLV 100.6.5."
    DEFVAL { "" }
    ::= { cerRpdDataEntry 42 }

cerRpdDataSupportsAdp OBJECT-TYPE
    SYNTAX TruthValue
    MAX-ACCESS read-only
    STATUS current
    DESCRIPTION
        "Indication of whether or not the RPD supports ADP.
         This is populated using vendor-specific TLV 21.8.1."
    DEFVAL { false }
    ::= { cerRpdDataEntry 43 }
    
cerRpdDataAdpNonOptimal OBJECT-TYPE
    SYNTAX      TruthValue
    MAX-ACCESS  read-only
    STATUS      current
    DESCRIPTION
        "The current setting of the ADP NonOptimal global parameter on the RPD.
         This is populated using vendor-specific TLV 21.4.5."
    DEFVAL { false }
    ::= { cerRpdDataEntry 44 }
    
cerRpdDataAdpSavedPreferredPort OBJECT-TYPE
    SYNTAX INTEGER {
        unset (0),
        port0 (1),
        port1 (2)
    }
    MAX-ACCESS  read-only
    STATUS      current
    DESCRIPTION
        "The current setting of the ADP SavedPreferredPort global parameter on the RPD.
         This is populated using vendor-specific TLV 21.4.6."
    DEFVAL { unset }
    ::= { cerRpdDataEntry 45 }

cerRpdDataAdpForward OBJECT-TYPE
    SYNTAX      TruthValue
    MAX-ACCESS  read-only
    STATUS      current
    DESCRIPTION
        "The current setting of the AdpForward global parameter on the RPD.
         This is populated using vendor-specific TLV 21.4.7."
    DEFVAL { false }
    ::= { cerRpdDataEntry 46 }    

cerRpdDataPnmCapabSupportedPnmTests OBJECT-TYPE
	SYNTAX BITS {
		aqprobes(0),
		rxmer(1),
		impnoisestats(2),
		dssymbolcapture(3),
		histogram(4)
	}
	MAX-ACCESS read-only
	STATUS current
	DESCRIPTION
		"This is the SupportedPnmTests attribute, corresponding to the RPD capability TLV type 50.64.1, and reports which PNM tests are supported by the
		RPD. The attribute is reported in BITS format, with value 0 for each bit definition indicating the RPD does not support the corresponding PNM test and
		value 1 for each bit definition indicating the RPD supports the corresponding PNM test. Note that UTSC is not represented in the bitmask defined
		above. The RPHY specification already defines UTSC capabilities via SpectrumCaptureCapabilities (TLV type 50.59). These capabilities are reflected in
		cerRpdDataPnmCapabUtscNumSacs and docsRphyRpdDevSacCapTable."
	DEFVAL { 'F8'H  }
	::= { cerRpdDataEntry 47 }

cerRpdDataPnmCapabUtscNumSacs OBJECT-TYPE
	SYNTAX Unsigned32
	MAX-ACCESS read-only
	STATUS current
	DESCRIPTION
		"This is the NumSacs attribute, corresponding to the RPD capability TLV type 50.59.1, and reports how many Spectrum Analysis Circuits (SACs) are
		supported by the RPD. Supported range is 0 to 255."
	DEFVAL { 0 }
	::= { cerRpdDataEntry 48 }
	
cerRpdDataPnmCapabUpcMinNumSymbols25Khz OBJECT-TYPE
	SYNTAX Unsigned32
	MAX-ACCESS read-only
	STATUS current
	DESCRIPTION
		"This is the MinNumSymbols25Khz attribute, corresponding to the RPD capability TLV type 50.64.2.1, and reports the minimum number of probe
		symbols that can be captured by the RPD in one UPC PNM test when an OFDMA channel is configured for 25 kHz subcarrier spacing. The valid range
		is 1 .. MaxNumPmapIes (TLV 50.54.3.1)."
	DEFVAL { 0 }
	::= { cerRpdDataEntry 49 }

cerRpdDataPnmCapabUpcMaxNumSymbols25Khz OBJECT-TYPE
	SYNTAX Unsigned32
	MAX-ACCESS read-only
	STATUS current
	DESCRIPTION
		"This is the MaxNumSymbols25Khz attribute, corresponding to the RPD capability TLV type 50.64.2.2, and reports the maximum number of probe
		symbols that can be captured by the RPD in one UPC PNM test when an OFDMA channel is configured for 25 kHz subcarrier spacing. The valid range
	is MinNumSymbols25Khz .. MaxNumPmapIes (TLV 50.54.3.1)."
	DEFVAL { 0 }
	::= { cerRpdDataEntry 50 }

cerRpdDataPnmCapabUpcMinNumSymbols50Khz OBJECT-TYPE
	SYNTAX Unsigned32
	MAX-ACCESS read-only
	STATUS current
	DESCRIPTION
		"This is the MinNumSymbols50Khz attribute, corresponding to the RPD capability TLV type 50.64.2.3, and reports the minimum number of probe
		symbols that can be captured by the RPD in one UPC PNM test when an OFDMA channel is configured for 50 kHz subcarrier spacing. The valid range
		is 1 .. MaxNumPmapIes (TLV 50.54.3.1)."
	DEFVAL { 0 }
	::= { cerRpdDataEntry 51 }

cerRpdDataPnmCapabUpcMaxNumSymbols50Khz OBJECT-TYPE
	SYNTAX Unsigned32
	MAX-ACCESS read-only
	STATUS current
	DESCRIPTION
		"This is the MaxNumSymbols50Khz attribute, corresponding to the RPD capability TLV type 50.64.2.4, and reports the maximum number of probe
		symbols that can be captured by the RPD in one UPC PNM test when an OFDMA channel is configured for 50 kHz subcarrier spacing. The valid range
		is MinNumSymbols50Khz .. MaxNumPmapIes (TLV 50.54.3.1)."
	DEFVAL { 0 }
	::= { cerRpdDataEntry 52 }

cerRpdDataPnmCapabUpcSupportsStaggeredPies OBJECT-TYPE
	SYNTAX TruthValue
	MAX-ACCESS read-only
	STATUS current
	DESCRIPTION
		"This is the SupportsStaggeredPies attribute, corresponding to the RPD capability TLV type 50.64.2.5, and reports whether the RPD supports UPC
		PNM tests with staggered Probe Information Elements, i.e., the RPD supports the use of a P-IE that specifies a staggered probe as the indicator for
		triggering the start of the capture and capturing consecutive symbols as defined by the P-IE subject to the RPD capability of the maximum number of
		symbols. A value of 1 (true) indicates that the SAC supports staggered P-IEs. A value of 0 (false) indicates that the SAC does not support staggered PIEs."
	DEFVAL { false }
	::= { cerRpdDataEntry 53 }

cerRpdDatadPnmCapabUpcSupportsDedicatedPwUpcRxMer OBJECT-TYPE
	SYNTAX TruthValue
	MAX-ACCESS read-only
	STATUS current
	DESCRIPTION
		"This is the SupportsDedicatedPwUpcRxMer attribute, corresponding to the RPD capability TLV type 50.64.2.6, and reports whether the RPD supports
		dedicated pseudowires for UPC and RxMER PNM tests. A value of 1 (true) indicates that the RPD supports dedicated pseudowires for UPC and
		RxMER tests. A value of 0 (false) indicates that the RPD does not support dedicated pseudowires for UPC and RxMER tests (i.e. the RPD only
		supports a shared pseudowire for UPC and RxMER tests)."
	DEFVAL { false }
	::= { cerRpdDataEntry 54}

cerRpdDataPnmCapabUpcSupportsFreqDomainSamples OBJECT-TYPE
	SYNTAX TruthValue
	MAX-ACCESS read-only
	STATUS current
	DESCRIPTION
		"This is the SupportsFreqDomainSamples attribute, corresponding to the RPD capability TLV type 50.64.2.7, and reports whether the RPD supports
		UPC PNM tests with samples represented in frequency domains. A value of 1 (true) indicates that the RPD supports samples represented in frequency
		domain. A value of 0 (false) indicates that the RPD does not support samples represented in frequency domain."
	DEFVAL { true }
	::= {cerRpdDataEntry 55}
--
-- E6000 RPHY L2TPv3 Tunnel Info Table
--

cerL2Tpv3TunnelInfoTable OBJECT-TYPE
    SYNTAX          SEQUENCE OF CerL2Tpv3TunnelInfoEntry 
    MAX-ACCESS      not-accessible
    STATUS          current
    DESCRIPTION
        "This table provides information about the L2TPv3 Tunnels on
         this core and, if reported by RPDs, other cores attached to this
         cores RPDs."
    ::= { cerRphyMib 24 }

cerL2Tpv3TunnelInfoEntry OBJECT-TYPE
    SYNTAX          CerL2Tpv3TunnelInfoEntry
    MAX-ACCESS      not-accessible
    STATUS          current
    DESCRIPTION
        "A conceptual row for this table.
        Entries in this table are created when an L2Tpv3 Session 
        becomes active."
    INDEX  { cerL2Tpv3TunnelInfoRpdIndex, cerL2Tpv3TunnelInfoCoreCCID } 
    ::= { cerL2Tpv3TunnelInfoTable 1 }

CerL2Tpv3TunnelInfoEntry ::= SEQUENCE {
        cerL2Tpv3TunnelInfoRpdIndex          CerRpdIndex,
        cerL2Tpv3TunnelInfoCoreCCID          Unsigned32,
        cerL2Tpv3TunnelInfoRpdCCID           Unsigned32,
        cerL2Tpv3TunnelInfoIpAddrType        InetAddressType,
        cerL2Tpv3TunnelInfoRpdLcceIpAddr     InetAddressIPv4or6,
        cerL2Tpv3TunnelInfoUnknownPwPkts     Counter64,
        cerL2Tpv3TunnelInfoRpdUnknownPwPkts  Counter64,
        cerL2Tpv3TunnelInfoRpdEnetPortIndex  Unsigned32,
        cerL2Tpv3TunnelInfoRpdEnetPortGcp    TruthValue
}

cerL2Tpv3TunnelInfoRpdIndex OBJECT-TYPE
    SYNTAX CerRpdIndex
    MAX-ACCESS not-accessible
    STATUS current
    DESCRIPTION
        "This object represents the RPD at the far end of the tunnel."
    ::= { cerL2Tpv3TunnelInfoEntry 1 }

cerL2Tpv3TunnelInfoCoreCCID OBJECT-TYPE
    SYNTAX          Unsigned32 (1..4294967295)
    MAX-ACCESS      not-accessible
    STATUS          current
    DESCRIPTION
        "The E6000 L2TPv3 CCID of the tunnel." 
    ::= { cerL2Tpv3TunnelInfoEntry 2 }

cerL2Tpv3TunnelInfoRpdCCID OBJECT-TYPE
    SYNTAX          Unsigned32 (0..4294967295)
    MAX-ACCESS      read-only
    STATUS          current
    DESCRIPTION
        "The RPD L2TPv3 CCID of the tunnel. Zero means not known." 
    ::= { cerL2Tpv3TunnelInfoEntry 3 }

cerL2Tpv3TunnelInfoIpAddrType OBJECT-TYPE
    SYNTAX InetAddressType
    MAX-ACCESS read-only
    STATUS current
    DESCRIPTION
        "Type of the tunnel IP address (IPv4, IPv6)."
    ::= { cerL2Tpv3TunnelInfoEntry 4 }

cerL2Tpv3TunnelInfoRpdLcceIpAddr OBJECT-TYPE
    SYNTAX InetAddressIPv4or6
    MAX-ACCESS read-only
    STATUS current
    DESCRIPTION
        "The tunnel IP address at the RPD."
    ::= { cerL2Tpv3TunnelInfoEntry 5 }

cerL2Tpv3TunnelInfoUnknownPwPkts OBJECT-TYPE
    SYNTAX Counter64
    MAX-ACCESS read-only
    STATUS current
    DESCRIPTION
        "The number of packets received on this tunnel with an unknown PW."
    ::= { cerL2Tpv3TunnelInfoEntry 6 }

cerL2Tpv3TunnelInfoRpdUnknownPwPkts OBJECT-TYPE
    SYNTAX Counter64
    MAX-ACCESS read-only
    STATUS current
    DESCRIPTION
        "The number of packets received on this tunnel with an unknown PW."
    ::= { cerL2Tpv3TunnelInfoEntry 7 }

cerL2Tpv3TunnelInfoRpdEnetPortIndex OBJECT-TYPE
    SYNTAX Unsigned32
    MAX-ACCESS read-only
    STATUS current
    DESCRIPTION
        "RPD Ethernet port index for this tunnel."
    DEFVAL { 0 }
    ::= { cerL2Tpv3TunnelInfoEntry 8 }

cerL2Tpv3TunnelInfoRpdEnetPortGcp OBJECT-TYPE
    SYNTAX TruthValue
    MAX-ACCESS read-only
    STATUS current
    DESCRIPTION
        "Indicates the presence of a GCP connection from the RPD Ethernet port for this tunnel."
    DEFVAL { false }
    ::= { cerL2Tpv3TunnelInfoEntry 9 }


--
-- RPD RPHY L2TPv3 Tunnel Info Table
--

cerRpdL2Tpv3TunnelInfoTable OBJECT-TYPE
    SYNTAX          SEQUENCE OF CerRpdL2Tpv3TunnelInfoEntry 
    MAX-ACCESS      not-accessible
    STATUS          current
    DESCRIPTION
        "This table provides information about the L2TPv3
         Tunnels on the E6000."
    ::= { cerRphyMib 25 }

cerRpdL2Tpv3TunnelInfoEntry OBJECT-TYPE
    SYNTAX          CerRpdL2Tpv3TunnelInfoEntry
    MAX-ACCESS      not-accessible
    STATUS          current
    DESCRIPTION
        "A conceptual row for this table.
        Entries in this table are created when an L2Tpv3 tunnel 
        is created in the RPD (to any core)."
    INDEX  { cerRpdL2Tpv3TunnelInfoRpdIndex, cerRpdL2Tpv3TunnelInfoRpdCCID } 
    ::= { cerRpdL2Tpv3TunnelInfoTable 1 }

CerRpdL2Tpv3TunnelInfoEntry ::= SEQUENCE {
        cerRpdL2Tpv3TunnelInfoRpdIndex          CerRpdIndex,
        cerRpdL2Tpv3TunnelInfoRpdCCID           Unsigned32,
        cerRpdL2Tpv3TunnelInfoCoreCCID          Unsigned32,
        cerRpdL2Tpv3TunnelInfoIpAddrType        InetAddressType,
        cerRpdL2Tpv3TunnelInfoCoreIpAddr        InetAddressIPv4or6,
        cerRpdL2Tpv3TunnelInfoUnknownPwPkts     Counter64
}

cerRpdL2Tpv3TunnelInfoRpdIndex OBJECT-TYPE
    SYNTAX          CerRpdIndex
    MAX-ACCESS      not-accessible
    STATUS          current
    DESCRIPTION
        "The RPD Index." 
    ::= { cerRpdL2Tpv3TunnelInfoEntry 1 }

cerRpdL2Tpv3TunnelInfoRpdCCID OBJECT-TYPE
    SYNTAX          Unsigned32 (1..4294967295)
    MAX-ACCESS      not-accessible
    STATUS          current
    DESCRIPTION
        "The RPD L2TPv3 CCID of the tunnel." 
    ::= { cerRpdL2Tpv3TunnelInfoEntry 2 }

cerRpdL2Tpv3TunnelInfoCoreCCID OBJECT-TYPE
    SYNTAX          Unsigned32 (1..4294967295)
    MAX-ACCESS      read-only
    STATUS          current
    DESCRIPTION
        "The E6000 L2TPv3 CCID of the tunnel." 
    ::= { cerRpdL2Tpv3TunnelInfoEntry 3 }

cerRpdL2Tpv3TunnelInfoIpAddrType OBJECT-TYPE
    SYNTAX InetAddressType
    MAX-ACCESS read-only
    STATUS current
    DESCRIPTION
        "Type of the tunnel IP address (IPv4, IPv6)."
    ::= { cerRpdL2Tpv3TunnelInfoEntry 4 }

cerRpdL2Tpv3TunnelInfoCoreIpAddr OBJECT-TYPE
    SYNTAX InetAddressIPv4or6
    MAX-ACCESS not-accessible
    STATUS current
    DESCRIPTION
        "The E6000 IP address of the tunnel."
    ::= { cerRpdL2Tpv3TunnelInfoEntry 5 }

cerRpdL2Tpv3TunnelInfoUnknownPwPkts OBJECT-TYPE
    SYNTAX Counter64
    MAX-ACCESS read-only
    STATUS current
    DESCRIPTION
        "The number of packets received on this tunnel with an unknown PW."
    ::= { cerRpdL2Tpv3TunnelInfoEntry 6 }

--
-- E6000 RPHY L2TPv3 Session Info Table
--

cerRphySessionInfoTable OBJECT-TYPE
    SYNTAX          SEQUENCE OF CerRphySessionInfoEntry 
    MAX-ACCESS      not-accessible
    STATUS          current
    DESCRIPTION
        "This table provides information about the L2TPv3
         PseudoWires (sessions) on the E6000."
    ::= { cerRphyMib 26 }

cerRphySessionInfoEntry OBJECT-TYPE
    SYNTAX          CerRphySessionInfoEntry
    MAX-ACCESS      not-accessible
    STATUS          current
    DESCRIPTION
        " Entries in this table are created when an L2Tpv3 Session 
          becomes active on the E6000 CER. There is one row per narrowcast 
          and per broadcast video channel per RPD, plus one row per RPD for DS
          DOCSIS channels, plus one row per DOCSIS US channel per RPD, plus
          one row per US and per DS OOB 55-1 channel per RPD, if supported."
    INDEX { cerRphySessionInfoIpAddrType, 
            cerRphySessionInfoCoreLcceIpAddr, 
            cerRphySessionInfoRpdLcceIpAddr, 
            cerRphySessionInfoDirection, 
            cerRphySessionInfoSessionId }
    ::= { cerRphySessionInfoTable 1 }

CerRphySessionInfoEntry ::= SEQUENCE {
        cerRphySessionInfoRpdIndex          CerRpdIndexOrZero,
        cerRphySessionInfoSessionId         Unsigned32,
        cerRphySessionInfoRpdSessionId      Unsigned32,
        cerRphySessionInfoCoreCCID          Unsigned32,
        cerRphySessionInfoSessionType       PwType,
        cerRphySessionInfoSessionSubtype    PwSubtype,
        cerRphySessionInfoOperStatus        PwOperState,
        cerRphySessionInfoPwStatus          PwStatus,
        cerRphySessionInfoErrorCode         PwErrorCode,
        cerRphySessionInfoCreationTime      TimeStamp,
        cerRphySessionInfoLastChangeTime    TimeStamp,
        cerRphySessionInfoOutOfSeqPkts      Counter64,
        cerRphySessionInfoIpAddrType        InetAddressType,
        cerRphySessionInfoEffectiveMtu      Unsigned32,
        cerRphySessionInfoDirection         INTEGER,
        cerRphySessionInfoRpdLcceIpAddr     InetAddressIPv4or6,
        cerRphySessionInfoCoreLcceIpAddr    InetAddressIPv4or6,
        cerRphySessionInfoChanType          INTEGER
}

cerRphySessionInfoRpdIndex OBJECT-TYPE
    SYNTAX          CerRpdIndexOrZero
    MAX-ACCESS      read-only
    STATUS          current
    DESCRIPTION
        "The RPD Index for this session." 
    ::= { cerRphySessionInfoEntry 1 }

cerRphySessionInfoSessionId OBJECT-TYPE
    SYNTAX          Unsigned32 (1..4294967295)
    MAX-ACCESS      not-accessible
    STATUS          current
    DESCRIPTION
        "The globally unique Core Session ID." 
    ::= { cerRphySessionInfoEntry 2 }

cerRphySessionInfoRpdSessionId OBJECT-TYPE
    SYNTAX          Unsigned32 (0..4294967295)
    MAX-ACCESS      read-only
    STATUS          current
    DESCRIPTION
        "The RPD Session ID." 
    ::= { cerRphySessionInfoEntry 3 }

cerRphySessionInfoCoreCCID OBJECT-TYPE
    SYNTAX          Unsigned32 (0..4294967295)
    MAX-ACCESS      read-only
    STATUS          current
    DESCRIPTION
        "The E6000 L2TPv3 CCID of the tunnel containing this session.
         Zero implies a static PW session."
    ::= { cerRphySessionInfoEntry 4 }

cerRphySessionInfoSessionType OBJECT-TYPE
    SYNTAX          PwType
    MAX-ACCESS      read-only
    STATUS          current
    DESCRIPTION
        "The Session type." 
    ::= { cerRphySessionInfoEntry 5 }

cerRphySessionInfoSessionSubtype OBJECT-TYPE
    SYNTAX          PwSubtype
    MAX-ACCESS      read-only
    STATUS          current
    DESCRIPTION
        "The Session subtype." 
    ::= { cerRphySessionInfoEntry 6 }

cerRphySessionInfoOperStatus OBJECT-TYPE
    SYNTAX PwOperState
    MAX-ACCESS read-only
    STATUS current
    DESCRIPTION
        "This object indicates the operational status of the PW; it
         does not reflect the status of the Customer Edge (CE) bound
         interface. It is set to down only if pwNotForwarding,
         psnFacingPwRxFault, or psnFacingPwTxFault indications are
         set in pwLocalStatus or pwRemoteStatus.
         It indicates lowerLayerDown if the only reason for
         not being in the up state is that either the outer tunnel
         or physical layer of the network side is in the 'down'
         state.
         All other states are declared based on the description
         of the PwOperStatusTC."
    DEFVAL { up }
    ::= { cerRphySessionInfoEntry 7 }

cerRphySessionInfoPwStatus OBJECT-TYPE
    SYNTAX PwStatus
    MAX-ACCESS read-only
    STATUS current
    DESCRIPTION
        "Indicates the status of the PW in the local node.
         The various indications in this object SHOULD be
         available independent of the ability of the local node to
         advertise them or the remote node to accept these status
         indications through the control protocol."
    ::= { cerRphySessionInfoEntry 8 }

cerRphySessionInfoErrorCode OBJECT-TYPE
    SYNTAX          PwErrorCode
    MAX-ACCESS      read-only
    STATUS          current
    DESCRIPTION
        "The error Code raised when pwOperStatus is down" 
    ::= { cerRphySessionInfoEntry 9 }

cerRphySessionInfoCreationTime OBJECT-TYPE
    SYNTAX          TimeStamp
    MAX-ACCESS      read-only
    STATUS          current
    DESCRIPTION
        "The E6000 sysUptime when the session first became active." 
    ::= { cerRphySessionInfoEntry 10 }

cerRphySessionInfoLastChangeTime OBJECT-TYPE
    SYNTAX          TimeStamp
    MAX-ACCESS      read-only
    STATUS          current
    DESCRIPTION
        "The E6000 sysUptime when the session last changed oper status." 
    ::= { cerRphySessionInfoEntry 11 }

cerRphySessionInfoOutOfSeqPkts OBJECT-TYPE
    SYNTAX          Counter64
    MAX-ACCESS      read-only
    STATUS          current
    DESCRIPTION
        "The number of packets received at the E6000 Core that were out-of-sequence." 
    ::= { cerRphySessionInfoEntry 12 }

cerRphySessionInfoIpAddrType OBJECT-TYPE
    SYNTAX InetAddressType
    MAX-ACCESS not-accessible
    STATUS current
    DESCRIPTION
        "Type of the session IP address (IPv4, IPv6)."
    ::= { cerRphySessionInfoEntry 13 }

cerRphySessionInfoEffectiveMtu OBJECT-TYPE
    SYNTAX Unsigned32
    MAX-ACCESS read-only
    STATUS current
    DESCRIPTION
        "The effective MTU used for DEPI/UEPI traffic on this PW to this RPD.
		 For unicast PWs, this is the value of cerRpdSessionInfoRpdMtu for this PW.
		 For broadcast PWs, it is the least value of cerRpdSessionInfoRpdMtu for 
		 all RPDs receiving the broadcast PW."
    ::= { cerRphySessionInfoEntry 14 }

cerRphySessionInfoDirection OBJECT-TYPE
    SYNTAX INTEGER {
        forward(0), 
        return(1)
    }
    MAX-ACCESS not-accessible
    STATUS current
    DESCRIPTION
        "This key attribute reports the direction of the
        session detailed in the instance. Valid values include:
        'forward' - Forward (downstream) direction toward the RPD.
        'return' - Return (upstream) direction toward the CCAP Core."
    ::= { cerRphySessionInfoEntry 15 }

cerRphySessionInfoRpdLcceIpAddr OBJECT-TYPE
    SYNTAX InetAddressIPv4or6
    MAX-ACCESS not-accessible
    STATUS current
    DESCRIPTION
        "The session IP address (unicast or multicast) at the RPD."
    ::= { cerRphySessionInfoEntry 16 }

cerRphySessionInfoCoreLcceIpAddr OBJECT-TYPE
    SYNTAX InetAddressIPv4or6
    MAX-ACCESS not-accessible
    STATUS current
    DESCRIPTION
        "This key attribute provides the LCCE IP address on the CCAP Core of a dynamic unicast
        session detailed in the instance. For a static unicast session, it is the engine sending the
        packets. For a broadcast session, it is the source address of the multicast stream for
        source-specific multicast, or zero for any-source multicast."
    ::= { cerRphySessionInfoEntry 17 }

cerRphySessionInfoChanType OBJECT-TYPE
    SYNTAX INTEGER {
        reserved(0),
        dsOfdm(1),
        dsOfdmPlc(2),
        dsScqam(3),
        usAtdma(4),
        usOfdma(5),
        scte551Fwd(6),
        scte551Ret(7),
        scte552Fwd(8),
        scte552Ret(9),
        ndf(10),
        ndr(11),
        pnmUtscSac(12),
        dtpComm(16)
    }
    MAX-ACCESS read-write
    STATUS      current
    DESCRIPTION
        "The 8-bit channel type of the DEPI channel selector ."
    REFERENCE
        "CM-SP-R-DEPI-I12-190307 Table 9"
    ::= { cerRphySessionInfoEntry 18 }

--
-- RPD RPHY L2TPv3 Session Info Table
--
cerRpdSessionInfoTable OBJECT-TYPE
    SYNTAX          SEQUENCE OF CerRpdSessionInfoEntry 
    MAX-ACCESS      not-accessible
    STATUS          current
    DESCRIPTION
        "This table provides information about the L2TPv3
         PseudoWires (sessions) on the RPDs. Sessions from
         Any core are included."
    ::= { cerRphyMib 27 }

cerRpdSessionInfoEntry OBJECT-TYPE
    SYNTAX          CerRpdSessionInfoEntry
    MAX-ACCESS      not-accessible
    STATUS          current
    DESCRIPTION
        "A conceptual row for this table.
        Entries in this table are created when an L2Tpv3 Session 
        becomes active."
    INDEX { cerRpdSessionInfoRpdIndex, 
            cerRpdSessionInfoIpAddrType,
            cerRpdSessionInfoCoreLcceIpAddr,
            cerRpdSessionInfoRpdLcceIpAddr,
            cerRpdSessionInfoDirection,
            cerRpdSessionInfoRpdSessionId }
    ::= { cerRpdSessionInfoTable 1 }

CerRpdSessionInfoEntry ::= SEQUENCE {
        cerRpdSessionInfoRpdIndex          CerRpdIndex,
        cerRpdSessionInfoRpdSessionId      Unsigned32,
        cerRpdSessionInfoRpdCCID           Unsigned32,
        cerRpdSessionInfoSessionType       PwType,
        cerRpdSessionInfoSessionSubtype    PwSubtype,
        cerRpdSessionInfoOperStatus        PwOperState,
        cerRpdSessionInfoPwStatus          PwStatus,
        cerRpdSessionInfoErrorCode         PwErrorCode,
        cerRpdSessionInfoCreationTime      TimeStamp,
        cerRpdSessionInfoLastChangeTime    TimeStamp,
        cerRpdSessionInfoOutOfSeqPkts      Counter64,
        cerRpdSessionInfoCoreSessionId     Unsigned32,
        cerRpdSessionInfoDirection         INTEGER,
        cerRpdSessionInfoIpAddrType        InetAddressType,
        cerRpdSessionInfoRpdLcceIpAddr     InetAddressIPv4or6,
        cerRpdSessionInfoCoreLcceIpAddr    InetAddressIPv4or6,
        cerRpdSessionInfoCoreIpAddr        InetAddressIPv4or6,
        cerRpdSessionInfoRpdMtu            Unsigned32,
        cerRpdSessionInfoEnetPortIndex     Unsigned32
}

cerRpdSessionInfoRpdIndex OBJECT-TYPE
    SYNTAX          CerRpdIndex
    MAX-ACCESS      not-accessible
    STATUS          current
    DESCRIPTION
        "The RPD Index." 
    ::= { cerRpdSessionInfoEntry 1 }

cerRpdSessionInfoRpdSessionId OBJECT-TYPE
    SYNTAX          Unsigned32 (1..4294967295)
    MAX-ACCESS      read-only
    STATUS          current
    DESCRIPTION
        "The RPD Session ID." 
    ::= { cerRpdSessionInfoEntry 2 }

cerRpdSessionInfoRpdCCID OBJECT-TYPE
    SYNTAX          Unsigned32 (1..4294967295)
    MAX-ACCESS      read-only
    STATUS          current
    DESCRIPTION
        "The RPDs L2TPv3 CCID of the tunnel containing this session." 
    ::= { cerRpdSessionInfoEntry 3 }

cerRpdSessionInfoSessionType OBJECT-TYPE
    SYNTAX          PwType
    MAX-ACCESS      read-only
    STATUS          current
    DESCRIPTION
        "The Session type." 
    ::= { cerRpdSessionInfoEntry 4 }

cerRpdSessionInfoSessionSubtype OBJECT-TYPE
    SYNTAX          PwSubtype
    MAX-ACCESS      read-only
    STATUS          current
    DESCRIPTION
        "The Session subtype." 
    ::= { cerRpdSessionInfoEntry 5 }

cerRpdSessionInfoOperStatus OBJECT-TYPE
    SYNTAX PwOperState
    MAX-ACCESS read-only
    STATUS current
    DESCRIPTION
        "This object indicates the operational status of the PW; it
         does not reflect the status of the Customer Edge (CE) bound
         interface. It is set to down only if pwNotForwarding,
         psnFacingPwRxFault, or psnFacingPwTxFault indications are
         set in pwLocalStatus or pwRemoteStatus.
         It indicates lowerLayerDown if the only reason for
         not being in the up state is that either the outer tunnel
         or physical layer of the network side is in the down
         state.
         All other states are declared based on the description
         of the PwOperStatusTC."
    ::= { cerRpdSessionInfoEntry 6 }

cerRpdSessionInfoPwStatus OBJECT-TYPE
    SYNTAX PwStatus
    MAX-ACCESS read-only
    STATUS current
    DESCRIPTION
        "Indicates the status of the PW in the local node.
          The various indications in this object SHOULD be
          available independent of the ability of the local node to
          advertise them or the remote node to accept these status
           indications through the control protocol."
    ::= { cerRpdSessionInfoEntry 7 }

cerRpdSessionInfoErrorCode OBJECT-TYPE
    SYNTAX          PwErrorCode
    MAX-ACCESS      read-only
    STATUS          current
    DESCRIPTION
        "The error Code raised when pwOperStatus is down" 
    ::= { cerRpdSessionInfoEntry 8 }

cerRpdSessionInfoCreationTime OBJECT-TYPE
    SYNTAX          TimeStamp
    MAX-ACCESS      read-only
    STATUS          current
    DESCRIPTION
        "The RPD sysUptime when the session first became active." 
    ::= { cerRpdSessionInfoEntry 9 }

cerRpdSessionInfoLastChangeTime OBJECT-TYPE
    SYNTAX          TimeStamp
    MAX-ACCESS      read-only
    STATUS          current
    DESCRIPTION
        "The RPD sysUptime when the session last changed oper status." 
    ::= { cerRpdSessionInfoEntry 10 }

cerRpdSessionInfoOutOfSeqPkts OBJECT-TYPE
    SYNTAX          Counter64
    MAX-ACCESS      read-only
    STATUS          current
    DESCRIPTION
        "The number of packets received at the RPD that were out-of-sequence." 
    ::= { cerRpdSessionInfoEntry 11 }

cerRpdSessionInfoCoreSessionId OBJECT-TYPE
    SYNTAX          Unsigned32 (1..4294967295)
    MAX-ACCESS      not-accessible
    STATUS          current
    DESCRIPTION
        "The Core Session ID." 
    ::= { cerRpdSessionInfoEntry 12 }

cerRpdSessionInfoDirection OBJECT-TYPE
    SYNTAX INTEGER {
        forward(0),
        return(1)
    }
    MAX-ACCESS not-accessible
    STATUS current
    DESCRIPTION
        "This key attribute reports the direction of the
        session detailed in the instance. Valid values include:
        'forward' - Forward (downstream) direction toward the RPD.
        'return' - Return (upstream) direction toward the CCAP Core."
    ::= { cerRpdSessionInfoEntry 13 }

cerRpdSessionInfoIpAddrType OBJECT-TYPE
    SYNTAX InetAddressType
    MAX-ACCESS not-accessible
    STATUS current
    DESCRIPTION
        "Type of the session IP address (IPv4, IPv6)."
    ::= { cerRpdSessionInfoEntry 14 }

cerRpdSessionInfoRpdLcceIpAddr OBJECT-TYPE
    SYNTAX InetAddressIPv4or6
    MAX-ACCESS not-accessible
    STATUS current
    DESCRIPTION
        "This key attribute provides the LCCE IP address on the RPD for a dynamic unicast session.
        For a static unicast session, it is the RPD Ethernet port address for the
        packets. For a broadcast session, it is the multicast group address for the packet stream."
    ::= { cerRpdSessionInfoEntry 15 }

cerRpdSessionInfoCoreLcceIpAddr OBJECT-TYPE
    SYNTAX InetAddressIPv4or6
    MAX-ACCESS not-accessible
    STATUS current
    DESCRIPTION
        "This key attribute provides the LCCE IP address on the CCAP Core of a dynamic unicast
        session detailed in the instance. For a static unicast session, it is the engine sending the
        packets. For a broadcast session, it is the source address of the multicast stream for
        source-specific multicast, or zero for any-source multicast."
    ::= { cerRpdSessionInfoEntry 16 }

cerRpdSessionInfoCoreIpAddr OBJECT-TYPE
    SYNTAX InetAddressIPv4or6
    MAX-ACCESS read-only
    STATUS current
    DESCRIPTION
        "This key attribute provides the IP address on the CCAP Core of a dynamic session and the IP address
        of the engine for a static session. For unicast and source-specific broadcast sessions, it matches
        cerRpdSessionInfoCoreLcceIpAddr, but differs for any-source broadcasts sessions;
        cerRpdSessionInfoCoreLcceIpAddr contains the null address for those sessions."
    ::= { cerRpdSessionInfoEntry 17 }

cerRpdSessionInfoRpdMtu OBJECT-TYPE
    SYNTAX Unsigned32
    MAX-ACCESS read-only
    STATUS current
    DESCRIPTION
        "The smaller of the supported MTU reported by this RPD when this PW is created and the MTU in the core."
    ::= { cerRpdSessionInfoEntry 18 }

cerRpdSessionInfoEnetPortIndex OBJECT-TYPE
    SYNTAX Unsigned32
    MAX-ACCESS read-only
    STATUS current
    DESCRIPTION
        "RPD Ethernet port index for this session."
    ::= { cerRpdSessionInfoEntry 19 }

--------------------------------------------------------------------------------------------------
-- RPD DEPI Channel Selector to Channel IfIndex Table
--------------------------------------------------------------------------------------------------

cerRpdChanSelectorTable OBJECT-TYPE
    SYNTAX SEQUENCE OF CerRpdChanSelectorEntry
    MAX-ACCESS not-accessible
    STATUS current
    DESCRIPTION
        "This table contains an entry for each PHY channel on each RPD.
         This could include channels configured on a different core."
    ::= { cerRphyMib 29 }

cerRpdChanSelectorEntry OBJECT-TYPE
    SYNTAX CerRpdChanSelectorEntry
    MAX-ACCESS not-accessible
    STATUS current
    DESCRIPTION
        "An entry for one PHY channel."
    INDEX { cerRpdChanSelectorRpdIndex, 
            cerRpdChanSelectorValue, 
            cerRpdChanSelectorDataPwId }
    ::= {cerRpdChanSelectorTable 1}

CerRpdChanSelectorEntry ::= SEQUENCE {
    cerRpdChanSelectorRpdIndex            CerRpdIndex,
    cerRpdChanSelectorValue               Unsigned32,
    cerRpdChanSelectorDepiChanId          Unsigned32,
    cerRpdChanSelectorDataPwId            Unsigned32,
    cerRpdChanSelectorPhyIfIndex          InterfaceIndexOrZero,
    cerRpdChanSelectorMacIfIndex          InterfaceIndexOrZero,
    cerRpdChanSelectorPwSubType           PwSubtype
}

cerRpdChanSelectorRpdIndex OBJECT-TYPE
    SYNTAX CerRpdIndex
    MAX-ACCESS not-accessible
    STATUS current
    DESCRIPTION
        "The index of the RPD."
    ::= { cerRpdChanSelectorEntry 1 }

cerRpdChanSelectorValue OBJECT-TYPE
    SYNTAX Unsigned32
    MAX-ACCESS   not-accessible
    STATUS current
    DESCRIPTION
        "DEPI channel selector for a channel on the RPD. This 24 bit number
         has the RPD RF port number in the upper 8 bits, the channel type in
         the middle 8 bits, and the channel ID in low 8 bits."
    REFERENCE
        "DEPI Table 9"
    ::= { cerRpdChanSelectorEntry 2 }

cerRpdChanSelectorDepiChanId OBJECT-TYPE
    SYNTAX Unsigned32 (0..255)
    MAX-ACCESS   read-only
    STATUS current
    DESCRIPTION
        "DEPI channel ID associated with this RPD channel selector.
         Zero means that this channel selector channel type does not
         use a DEPI channel ID (only DOCSIS DS channels have a channel ID)."
    ::= { cerRpdChanSelectorEntry 3 }

cerRpdChanSelectorDataPwId OBJECT-TYPE
    SYNTAX Unsigned32
    MAX-ACCESS   not-accessible
    STATUS current
    DESCRIPTION
        "Rpd Pseudowire ID of DEPI session carrying this channel."
    ::= { cerRpdChanSelectorEntry 4 }

cerRpdChanSelectorPhyIfIndex OBJECT-TYPE
    SYNTAX InterfaceIndexOrZero 
    MAX-ACCESS read-only
    STATUS current
    DESCRIPTION
        "The E6000 RPD IfIndex of this PHY channel. Zero if the channel
         is configured by a different core."
    ::= { cerRpdChanSelectorEntry 5 }

cerRpdChanSelectorMacIfIndex OBJECT-TYPE
    SYNTAX InterfaceIndexOrZero 
    MAX-ACCESS read-only
    STATUS current
    DESCRIPTION
        "The E6000 IfIndex of the MAC channel associated with this RPD channel.
    Zero if the channel is configured by a different core."
    ::= { cerRpdChanSelectorEntry 6 }

cerRpdChanSelectorPwSubType OBJECT-TYPE
    SYNTAX          PwSubtype
    MAX-ACCESS      read-only
    STATUS          current
    DESCRIPTION
        "The Session subtype for this PW." 
    ::= { cerRpdChanSelectorEntry 7 }


--------------------------------------------------------------------------------------------------
-- OOB 55-1 DS IP Address to Channel table
--------------------------------------------------------------------------------------------------

cerOob551DsAddrToChanTable OBJECT-TYPE
    SYNTAX SEQUENCE OF CerOob551DsAddrToChanEntry
    MAX-ACCESS not-accessible
    STATUS current
    DESCRIPTION
        "This table contains the mapping of incoming IP packet streams to OOB 55-1 DS channels."
    ::= { cerRphyMib 32 }

cerOob551DsAddrToChanEntry OBJECT-TYPE
    SYNTAX CerOob551DsAddrToChanEntry
    MAX-ACCESS not-accessible
    STATUS current
    DESCRIPTION
        "An entry for the table."
    INDEX { cerOob551DsAddrToChanAddrType, cerOob551DsAddrToChanDestIpAddr,
            cerOob551DsAddrToChanDestUdpPort }
    ::= {cerOob551DsAddrToChanTable 1}

CerOob551DsAddrToChanEntry ::= SEQUENCE {
    cerOob551DsAddrToChanAddrType          InetAddressType,
    cerOob551DsAddrToChanDestIpAddr        InetAddressIPv4or6,
    cerOob551DsAddrToChanDestUdpPort       InetPortNumber,
    cerOob551DsAddrToChanDsIfIndex         InterfaceIndex,
    cerOob551DsAddrToChanOmIpAddr          InetAddressIPv4or6
}

cerOob551DsAddrToChanAddrType OBJECT-TYPE
    SYNTAX InetAddressType
    MAX-ACCESS   not-accessible
    STATUS current
    DESCRIPTION
        "Type of OM address (ipv4 or ipv6)."
    DEFVAL { ipv4 }
    ::= {cerOob551DsAddrToChanEntry 1}

cerOob551DsAddrToChanDestIpAddr OBJECT-TYPE
    SYNTAX InetAddressIPv4or6
    MAX-ACCESS not-accessible
    STATUS current
    DESCRIPTION
        "The OOB 55-1 OM IP source address for incoming DS OOB 55-1 packets."
    ::= {cerOob551DsAddrToChanEntry 2}

cerOob551DsAddrToChanDestUdpPort OBJECT-TYPE
    SYNTAX InetPortNumber
    MAX-ACCESS not-accessible
    STATUS current
    DESCRIPTION
        "OM UDP Destination port for incoming DS OOB 55-1 packets."
    ::= { cerOob551DsAddrToChanEntry 3}

cerOob551DsAddrToChanDsIfIndex OBJECT-TYPE
    SYNTAX InterfaceIndex 
    MAX-ACCESS read-only
    STATUS current
    DESCRIPTION
        "The E6000 IfIndex of the destination MAC channel DS OOB 55-1 input stream. "
    ::= { cerOob551DsAddrToChanEntry 4}

cerOob551DsAddrToChanOmIpAddr OBJECT-TYPE
    SYNTAX InetAddressIPv4or6
    MAX-ACCESS read-create
    STATUS current
    DESCRIPTION
        "The OOB 55-1 OM IP source address for incoming DS OOB 55-1 packets."
    ::= { cerOob551DsAddrToChanEntry 5}

--------------------------------------------------------------------------------------------------
-- OOB 55-1 RPD US RF Port List Group table
--------------------------------------------------------------------------------------------------

cerOobRpdUsRfPortTable OBJECT-TYPE
    SYNTAX SEQUENCE OF CerOobRpdUsRfPortEntry
    MAX-ACCESS not-accessible
    STATUS current
    DESCRIPTION
        "This table contains the lists of US RPD RF ports for assignment
         to an OOB 55-1 virtual RF port."
    ::= { cerRphyMib 37 }

cerOobRpdUsRfPortEntry OBJECT-TYPE
    SYNTAX CerOobRpdUsRfPortEntry
    MAX-ACCESS not-accessible
    STATUS current
    DESCRIPTION
        "An entry for the table."
    INDEX { cerOobRpdUsRfPortRpdGrpName, cerOobRpdUsRfPortRpdIndex, cerOobRpdUsRfPortRpdPortId }
    ::= {cerOobRpdUsRfPortTable 1}

CerOobRpdUsRfPortEntry ::= SEQUENCE {
    cerOobRpdUsRfPortRpdGrpName                 NodeName,
    cerOobRpdUsRfPortRpdIndex                   CerRpdIndex,
    cerOobRpdUsRfPortRpdPortId                  Unsigned32,
    cerOobRpdUsRfPortRowStatus                  RowStatus
}

cerOobRpdUsRfPortRpdGrpName OBJECT-TYPE
    SYNTAX NodeName
    MAX-ACCESS not-accessible
    STATUS current
    DESCRIPTION
        "Name of the Fiber node."
    ::= { cerOobRpdUsRfPortEntry 1}

cerOobRpdUsRfPortRpdIndex OBJECT-TYPE
    SYNTAX CerRpdIndex
    MAX-ACCESS not-accessible
    STATUS current
    DESCRIPTION
        "The index of the RPD."
    ::= {cerOobRpdUsRfPortEntry 2}

cerOobRpdUsRfPortRpdPortId OBJECT-TYPE
    SYNTAX Unsigned32 (1..4)
    MAX-ACCESS not-accessible
    STATUS current
    DESCRIPTION
        "The RF port number on the RPD for this channel."
    ::= {cerOobRpdUsRfPortEntry 3}

cerOobRpdUsRfPortRowStatus   OBJECT-TYPE
    SYNTAX      RowStatus
    MAX-ACCESS  read-create
    STATUS      current
    DESCRIPTION
        "The RowStatus for controlling entries in this table. 
         Allowed values are createAndGo, destroy, and active."
    ::= { cerOobRpdUsRfPortEntry 4 }


--------------------------------------------------------------------------------------------------
-- RPD Downstream RF Port Exclusion table
--------------------------------------------------------------------------------------------------

cerRpdDsExclTable OBJECT-TYPE
    SYNTAX SEQUENCE OF CerRpdDsExclEntry
    MAX-ACCESS not-accessible
    STATUS current
    DESCRIPTION
        "This table contains RPD Exclusions for OFDM channels."
    ::= { cerRphyMib 40 }

cerRpdDsExclEntry OBJECT-TYPE
    SYNTAX CerRpdDsExclEntry
    MAX-ACCESS not-accessible
    STATUS current
    DESCRIPTION
        "An entry for the table."
    INDEX { cerRpdDsExclRpdIndex, cerRpdDsExclRpdRfPortId, cerRpdDsExclLowFreq }
    ::= {cerRpdDsExclTable 1}

CerRpdDsExclEntry ::= SEQUENCE {
    cerRpdDsExclRpdIndex              CerRpdIndex,
    cerRpdDsExclRpdRfPortId           Unsigned32,
    cerRpdDsExclLowFreq               Integer32,
    cerRpdDsExclHighFreq              Integer32,
    cerRpdDsExclRowStatus             RowStatus
}

cerRpdDsExclRpdIndex OBJECT-TYPE
    SYNTAX CerRpdIndex
    MAX-ACCESS not-accessible
    STATUS current
    DESCRIPTION
        "Global index for this RPD."
    ::= { cerRpdDsExclEntry 1}

cerRpdDsExclRpdRfPortId OBJECT-TYPE
    SYNTAX Unsigned32 (1..4)
    MAX-ACCESS not-accessible
    STATUS current
    DESCRIPTION
        "Index of DS RF port on the RPD."
    ::= { cerRpdDsExclEntry 2}

cerRpdDsExclLowFreq OBJECT-TYPE
    SYNTAX      Integer32 (108000000..1217000000)
    UNITS       "Hertz"
    MAX-ACCESS  read-create
    STATUS      current
    DESCRIPTION
        "The low edge of the exclusion on this RPD RF port."
    ::= { cerRpdDsExclEntry 3 }

cerRpdDsExclHighFreq OBJECT-TYPE
    SYNTAX      Integer32 (109000000..1218000000)
    UNITS       "Hertz"
    MAX-ACCESS  read-create
    STATUS      current
    DESCRIPTION
        "The high edge of the exclusion on this RPD RF port."
    ::= { cerRpdDsExclEntry 4 }

cerRpdDsExclRowStatus OBJECT-TYPE
    SYNTAX      RowStatus
    MAX-ACCESS  read-create
    STATUS      current
    DESCRIPTION
        "The RowStatus for controlling entries in this table. 
         Allowed values are createAndGo, destroy, and active."
    ::= { cerRpdDsExclEntry 5 }

--------------------------------------------------------------------------------------------------
-- RPD Upstream RF Port Exclusion table
--------------------------------------------------------------------------------------------------

cerRpdUsExclTable OBJECT-TYPE
    SYNTAX SEQUENCE OF CerRpdUsExclEntry
    MAX-ACCESS not-accessible
    STATUS current
    DESCRIPTION
        "This table contains RPD Exclusions for OFDMA channels."
    ::= { cerRphyMib 41 }

cerRpdUsExclEntry OBJECT-TYPE
    SYNTAX CerRpdUsExclEntry
    MAX-ACCESS not-accessible
    STATUS current
    DESCRIPTION
        "An entry for the table."
    INDEX { cerRpdUsExclRpdIndex, cerRpdUsExclRpdRfPortId, cerRpdUsExclLowFreq }
    ::= {cerRpdUsExclTable 1}

CerRpdUsExclEntry ::= SEQUENCE {
    cerRpdUsExclRpdIndex              CerRpdIndex,
    cerRpdUsExclRpdRfPortId           Unsigned32,
    cerRpdUsExclLowFreq               Integer32,
    cerRpdUsExclHighFreq              Integer32,
    cerRpdUsExclRowStatus             RowStatus
}

cerRpdUsExclRpdIndex OBJECT-TYPE
    SYNTAX CerRpdIndex
    MAX-ACCESS not-accessible
    STATUS current
    DESCRIPTION
        "Global index for this RPD."
    ::= { cerRpdUsExclEntry 1}

cerRpdUsExclRpdRfPortId OBJECT-TYPE
    SYNTAX Unsigned32 (1..4)
    MAX-ACCESS not-accessible
    STATUS current
    DESCRIPTION
        "Index of DS RF port on the RPD."
    ::= { cerRpdUsExclEntry 2}

cerRpdUsExclLowFreq OBJECT-TYPE
    SYNTAX      Integer32 (5000000..204000000)
    UNITS       "Hertz"
    MAX-ACCESS  read-create
    STATUS      current
    DESCRIPTION
        "The low edge of the exclusion on this RPD RF port."
    ::= { cerRpdUsExclEntry 3 }

cerRpdUsExclHighFreq OBJECT-TYPE
    SYNTAX      Integer32 (5000000..204000000)
    UNITS       "Hertz"
    MAX-ACCESS  read-create
    STATUS      current
    DESCRIPTION
        "The high edge of the exclusion on this RPD RF port."
    ::= { cerRpdUsExclEntry 4 }

cerRpdUsExclRowStatus OBJECT-TYPE
    SYNTAX      RowStatus
    MAX-ACCESS  read-create
    STATUS      current
    DESCRIPTION
        "The RowStatus for controlling entries in this table. 
         Allowed values are createAndGo, destroy, and active."
    ::= { cerRpdUsExclEntry 5 }

--------------------------------------------------------------------------------------------------
-- RPD Vendor Pre-Configuration table
--------------------------------------------------------------------------------------------------
cerRphyVspTable OBJECT-TYPE
    SYNTAX SEQUENCE OF CerRphyVspEntry
    MAX-ACCESS not-accessible
    STATUS current
    DESCRIPTION
        "This table contains RPD Vendor-Specific Pre-configuration data to
         be sent by a core to the RPD at initialization time."
    ::= { cerRphyMib 42 }

cerRphyVspEntry OBJECT-TYPE
    SYNTAX CerRphyVspEntry
    MAX-ACCESS not-accessible
    STATUS current
    DESCRIPTION
        "An entry for the table."
    INDEX { cerRphyVspVendorOid }
    ::= { cerRphyVspTable 1 }

CerRphyVspEntry ::= SEQUENCE {
    cerRphyVspVendorOid       Unsigned32,
    cerRphyVspSelector        DisplayString,
    cerRphyVspSetting         OCTET STRING,
    cerRphyVspRowStatus       RowStatus
}

cerRphyVspVendorOid OBJECT-TYPE
    SYNTAX Unsigned32 (1..65536) 
    MAX-ACCESS  not-accessible
    STATUS      current
    DESCRIPTION
        "OID of the RPD vendor."
    REFERENCE
        "https://www.iana.org/assignments/enterprise-numbers/enterprise-numbers"
    ::= { cerRphyVspEntry 1 }

cerRphyVspSelector OBJECT-TYPE 
   SYNTAX       DisplayString (SIZE(1..16))
   MAX-ACCESS   read-create
   STATUS       current
   DESCRIPTION
       "The VSP setting for the RPD."
   ::= { cerRphyVspEntry 2 } 

cerRphyVspSetting OBJECT-TYPE 
   SYNTAX       OCTET STRING (SIZE (1..1024))
   MAX-ACCESS   read-create
   STATUS       current
   DESCRIPTION
       "The VSP opaque information to be sent to the RPD."
   ::= { cerRphyVspEntry 3 } 

cerRphyVspRowStatus OBJECT-TYPE
    SYNTAX      RowStatus
    MAX-ACCESS  read-create
    STATUS      current
    DESCRIPTION
        "The RowStatus for controlling entries in this table. 
         Allowed values are createAndGo, destroy, and active."
    ::= { cerRphyVspEntry 4 }
           

--------------------------------------------------------------------------------------------------
-- Global Downstream CW tone Configuration table
--------------------------------------------------------------------------------------------------

cerRphyCwToneTable OBJECT-TYPE
    SYNTAX SEQUENCE OF CerRphyCwToneEntry
    MAX-ACCESS not-accessible
    STATUS current
    DESCRIPTION
        " This table contains global CW tone configuration. "
    ::= { cerRphyMib 43 }

cerRphyCwToneEntry OBJECT-TYPE
    SYNTAX CerRphyCwToneEntry
    MAX-ACCESS not-accessible
    STATUS current
    DESCRIPTION
        "An entry for the table."
    INDEX { cerRphyCwToneFreq }
    ::= { cerRphyCwToneTable 1 }

CerRphyCwToneEntry ::= SEQUENCE {
    cerRphyCwToneFreq               Unsigned32,
    cerRphyCwTonePowerAdj           TenthdB,
    cerRphyCwToneUsesDedicatedGen   TruthValue,
    cerRphyCwToneRowStatus          RowStatus
}

cerRphyCwToneFreq OBJECT-TYPE
    SYNTAX      Unsigned32 (5000000..1218000000)
    UNITS       "Hertz"
    MAX-ACCESS not-accessible
    STATUS      current
    DESCRIPTION
        "The CW tone frequency."
    ::= { cerRphyCwToneEntry 1 }

cerRphyCwTonePowerAdj OBJECT-TYPE
    SYNTAX      TenthdB
    UNITS       "TenthdB"
    MAX-ACCESS  read-create
    STATUS      current
    DESCRIPTION
        "The RPD RF port power adjustment for the CW tone."
    DEFVAL { 0 }
    ::= { cerRphyCwToneEntry 2 }

cerRphyCwToneUsesDedicatedGen OBJECT-TYPE
    SYNTAX TruthValue
    MAX-ACCESS   read-only
    STATUS current
    DESCRIPTION
        "Set to true if this the RPD MUST use a dedicated tone generator
         for this CW tone.  Dedicated tones use TLV 6.7 for RPD configuration.
         Non-dedicated townes use TLVs 62.5, 62.6 (value 5), and 62.16."
    DEFVAL { true }
    ::= { cerRphyCwToneEntry 3 }

cerRphyCwToneRowStatus OBJECT-TYPE
    SYNTAX      RowStatus
    MAX-ACCESS  read-create
    STATUS      current
    DESCRIPTION
        "The RowStatus for controlling entries in this table. 
         Allowed values are createAndGo, destroy, and active."
    ::= { cerRphyCwToneEntry 4 }

--------------------------------------------------------------------------------------------------
-- RPD Downstream CW tone Configuration table
--------------------------------------------------------------------------------------------------

cerRpdCwToneTable OBJECT-TYPE
    SYNTAX SEQUENCE OF CerRpdCwToneEntry
    MAX-ACCESS not-accessible
    STATUS current
    DESCRIPTION
        "This table contains CW tone configuration for a single RPD DS
         RF port. Any row for an RPD DS port in this table blocks
         use on this RPD of all rows in the global CW tone configuration 
         for the same RF port ID."
    ::= { cerRphyMib 44 }

cerRpdCwToneEntry OBJECT-TYPE
    SYNTAX CerRpdCwToneEntry
    MAX-ACCESS not-accessible
    STATUS current
    DESCRIPTION
        "An entry for the table."
    INDEX { cerRpdCwToneRpdIndex, cerRpdCwToneRfPortId, cerRpdCwToneFreq }
    ::= { cerRpdCwToneTable 1 }

CerRpdCwToneEntry ::= SEQUENCE {
    cerRpdCwToneRpdIndex           CerRpdIndex,
    cerRpdCwToneRfPortId           Unsigned32,
    cerRpdCwToneFreq               Unsigned32,
    cerRpdCwTonePowerAdj           TenthdB,
    cerRpdCwToneUsesDedicatedGen   TruthValue,
    cerRpdCwToneRowStatus          RowStatus
}

cerRpdCwToneRpdIndex OBJECT-TYPE
    SYNTAX CerRpdIndex
    MAX-ACCESS not-accessible
    STATUS current
    DESCRIPTION
        "Global index for this RPD."
    ::= { cerRpdCwToneEntry 1 }

cerRpdCwToneRfPortId OBJECT-TYPE
    SYNTAX Unsigned32 (1..4)
    MAX-ACCESS not-accessible
    STATUS current
    DESCRIPTION
        "Index of DS RF port on the RPD."
    ::= { cerRpdCwToneEntry 2 }

cerRpdCwToneFreq OBJECT-TYPE
    SYNTAX      Unsigned32 (54000000..1218000000)
    UNITS       "Hertz"
    MAX-ACCESS not-accessible
    STATUS      current
    DESCRIPTION
        "The CW tone frequency."
    ::= { cerRpdCwToneEntry 3 }

cerRpdCwTonePowerAdj OBJECT-TYPE
    SYNTAX      TenthdB
    UNITS       "TenthdB"
    MAX-ACCESS  read-create
    STATUS      current
    DESCRIPTION
        "The RPD RF port power adjustment for the CW tone."
    DEFVAL { 0 }
    ::= { cerRpdCwToneEntry 4 }

cerRpdCwToneUsesDedicatedGen OBJECT-TYPE
    SYNTAX TruthValue
    MAX-ACCESS   read-only
    STATUS current
    DESCRIPTION
        "Set to true if this the RPD MUST use a dedicated tone generator
         for this CW tone.  Dedicated tones use the TLV 6.7 for RPD configuration.
         Non-dedicated tones use TLVs 62.5, 62.6 (value 5), and 62.16."
    DEFVAL { true }
    ::= {cerRpdCwToneEntry 5 }

cerRpdCwToneRowStatus OBJECT-TYPE
    SYNTAX      RowStatus
    MAX-ACCESS  read-create
    STATUS      current
    DESCRIPTION
        "The RowStatus for controlling entries in this table. 
         Allowed values are createAndGo, destroy, and active."
    ::= { cerRpdCwToneEntry 6 }

cerRphyStatsGroup OBJECT IDENTIFIER ::= { cerRphyMib 45 }

cerRphyLocalConfigFilePresent OBJECT-TYPE
    SYNTAX TruthValue
    MAX-ACCESS  read-only
    STATUS      current
    DESCRIPTION
        "Set to true if a 'write local-config-file' is executed, set to false if an
         'erase local-config-file' is executed. Reflects whether a local config file
         is present on the system or not."
    DEFVAL { false }
    ::= { cerRphyStatsGroup 1 }

cerRphyConfigFileProcessingStatus OBJECT-TYPE
    SYNTAX INTEGER {
        processedNoErrors(1),
        processedWithErrors(2),
        notProcessed(3)
    }
    MAX-ACCESS read-only
    STATUS current
    DESCRIPTION
        "Set to ProcessedNoErrors when config file is processed
         without any command errors; set to ProcessedWithErrors 
         if one or more commands in the config file encounter 
         errors, set to NotProcessed if the device did not 
         use any config file for any reason."
    DEFVAL { notProcessed }
    ::= { cerRphyStatsGroup 2 }

--------------------------------------------------------------------------------------------------
-- RPD Channel Impaired Status table
--------------------------------------------------------------------------------------------------

cerRpdChanImpairedTable OBJECT-TYPE
    SYNTAX SEQUENCE OF CerRpdChanImpairedEntry
    MAX-ACCESS not-accessible
    STATUS current
    DESCRIPTION
        "This table contains all PHY Channels with operational
         state notPresenton in-service RPDs."
    ::= { cerRphyMib 46 }

cerRpdChanImpairedEntry OBJECT-TYPE
    SYNTAX CerRpdChanImpairedEntry
    MAX-ACCESS not-accessible
    STATUS current
    DESCRIPTION
        "An entry for the table."
        INDEX { cerRpdChanImpairedIfIndex, cerRpdChanImpairedRpdIndex, cerRpdChanImpairedRfPortId}
    ::= {cerRpdChanImpairedTable 1}

CerRpdChanImpairedEntry ::= SEQUENCE {
    cerRpdChanImpairedIfIndex            InterfaceIndex,
    cerRpdChanImpairedRpdIndex           CerRpdIndex,
    cerRpdChanImpairedRfPortId           Unsigned32,
    cerRpdChanImpairedRpdIfIndex         InterfaceIndex,
    cerRpdChanImpairedTimestamp          TimeStamp
}

cerRpdChanImpairedIfIndex OBJECT-TYPE
    SYNTAX InterfaceIndex
    MAX-ACCESS not-accessible
    STATUS current
    DESCRIPTION
        "IfIndex of the MAC channel that is impaired."
    ::= { cerRpdChanImpairedEntry 1 }

cerRpdChanImpairedRpdIndex OBJECT-TYPE
    SYNTAX CerRpdIndex
    MAX-ACCESS not-accessible
    STATUS current
    DESCRIPTION
        "Global index for this RPD."
    ::= { cerRpdChanImpairedEntry 2 }

cerRpdChanImpairedRfPortId OBJECT-TYPE
    SYNTAX Unsigned32 (1..4)
    MAX-ACCESS not-accessible
    STATUS current
    DESCRIPTION
        "Index of DS RF port on the RPD for the impaired channel."
    ::= { cerRpdChanImpairedEntry 3 }

cerRpdChanImpairedRpdIfIndex  OBJECT-TYPE
    SYNTAX      InterfaceIndex
    MAX-ACCESS  read-only
    STATUS      current
    DESCRIPTION
        "The PHY channel ifIndex of the impaired channel."
    ::= { cerRpdChanImpairedEntry 4 }

cerRpdChanImpairedTimestamp  OBJECT-TYPE
    SYNTAX      TimeStamp
    MAX-ACCESS  read-only
    STATUS      current
    DESCRIPTION
        "The value of E6000 sysUpTime when this channel was impaired."
    ::= { cerRpdChanImpairedEntry 5 }


--------------------------------------------------------------------------------------------------
-- RPHY AUX Core IP Address table
--------------------------------------------------------------------------------------------------

cerRphyAuxCoreTable OBJECT-TYPE
    SYNTAX      SEQUENCE OF CerRphyAuxCoreEntry
    MAX-ACCESS  not-accessible
    STATUS      current
    DESCRIPTION
        "This table contains the IP addresses of AUX cores to be sent in TLV 88 to RPDs."
    ::= { cerRphyMib 47 }

cerRphyAuxCoreEntry OBJECT-TYPE
    SYNTAX      CerRphyAuxCoreEntry
    MAX-ACCESS  not-accessible
    STATUS      current
    DESCRIPTION
        "An entry for the table."
    INDEX { cerRphyAuxCoreAddrType, cerRphyAuxCoreIpAddr }
    ::= { cerRphyAuxCoreTable 1 }

CerRphyAuxCoreEntry ::= SEQUENCE {
    cerRphyAuxCoreAddrType           InetAddressType,
    cerRphyAuxCoreIpAddr             InetAddressIPv4or6,
    cerRphyAuxCoreDescription        DisplayString,
    cerRphyAuxCoreRowStatus          RowStatus
}

cerRphyAuxCoreAddrType OBJECT-TYPE
    SYNTAX      InetAddressType
    MAX-ACCESS  not-accessible
    STATUS      current
    DESCRIPTION
        "Type of the AUX Core IP address; only IPv4 and IPv6 are allowed."
    ::= { cerRphyAuxCoreEntry 1 }

cerRphyAuxCoreIpAddr OBJECT-TYPE
    SYNTAX      InetAddressIPv4or6
    MAX-ACCESS  not-accessible
    STATUS      current
    DESCRIPTION
        "The IP address of this AUX core.  Only length 4 for IPv4 and length 16
         for IPv6 are allowed."
    ::= { cerRphyAuxCoreEntry 2 }

cerRphyAuxCoreDescription OBJECT-TYPE
    SYNTAX      DisplayString (SIZE(0..32))
    MAX-ACCESS  read-create
    STATUS      current
    DESCRIPTION
        "The description of the AUX core."
    DEFVAL { "" }
    ::= { cerRphyAuxCoreEntry 3 }

cerRphyAuxCoreRowStatus   OBJECT-TYPE
    SYNTAX      RowStatus
    MAX-ACCESS  read-create
    STATUS      current
    DESCRIPTION
        "The RowStatus for controlling entries in this table. 
         Allowed values are createAndGo, destroy, and active."
    ::= { cerRphyAuxCoreEntry 4 }

--------------------------------------------------------------------------------------------------
-- RPHY AUX Core Status table
--------------------------------------------------------------------------------------------------

cerRpdAuxCoreStatusTable OBJECT-TYPE
    SYNTAX      SEQUENCE OF CerRpdAuxCoreStatusEntry
    MAX-ACCESS  not-accessible
    STATUS      current
    DESCRIPTION
        "This table contains status of AUX cores for RPDs as reported via a
         General notification (TLV 86) of type AuxCoreResultNotification in TLV 86.1."
    ::= { cerRphyMib 48 }

cerRpdAuxCoreStatusEntry OBJECT-TYPE
    SYNTAX      CerRpdAuxCoreStatusEntry
    MAX-ACCESS  not-accessible
    STATUS      current
    DESCRIPTION
        "An entry for the table."
    INDEX { cerRpdAuxCoreStatusRpdIndex, cerRpdAuxCoreStatusAddrType,
            cerRpdAuxCoreStatusIpAddr }
    ::= { cerRpdAuxCoreStatusTable 1 }

CerRpdAuxCoreStatusEntry ::= SEQUENCE {
    cerRpdAuxCoreStatusRpdIndex           CerRpdIndex,
    cerRpdAuxCoreStatusAddrType           InetAddressType,
    cerRpdAuxCoreStatusIpAddr             InetAddressIPv4or6,
    cerRpdAuxCoreStatusResult             INTEGER,
    cerRpdAuxCoreStatusFailureType        INTEGER
}

cerRpdAuxCoreStatusRpdIndex OBJECT-TYPE
    SYNTAX      CerRpdIndex
    MAX-ACCESS  not-accessible
    STATUS      current
    DESCRIPTION
        "Global index for this RPD."
    ::= { cerRpdAuxCoreStatusEntry 1 }

cerRpdAuxCoreStatusAddrType OBJECT-TYPE
    SYNTAX      InetAddressType
    MAX-ACCESS  accessible-for-notify
    STATUS      current
    DESCRIPTION
        "Type of the AUX Core IP address; only IPv4 and IPv6 are allowed."
    ::= { cerRpdAuxCoreStatusEntry 2 }

cerRpdAuxCoreStatusIpAddr OBJECT-TYPE
    SYNTAX      InetAddressIPv4or6
    MAX-ACCESS  accessible-for-notify
    STATUS      current
    DESCRIPTION
        "The IP address of this AUX core."
    ::= { cerRpdAuxCoreStatusEntry 3 }

cerRpdAuxCoreStatusResult OBJECT-TYPE
    SYNTAX INTEGER {
            unknown(0),
            operational(1),
            corenotactive(2),
            failure(3)
    }
    MAX-ACCESS  read-only
    STATUS      current
    DESCRIPTION
        "The result notification for the AUX core (TLV 86.6 + 1)."
    DEFVAL { unknown }
    ::= { cerRpdAuxCoreStatusEntry 4 }

cerRpdAuxCoreStatusFailureType OBJECT-TYPE
    SYNTAX INTEGER {
            none(0),
            authentication(1),
            otherActivePrincipalCore(2),
            waitIraRetriesExceeded(3),
            waitConfigRetriesExceeded(4),
            initTcpConnFail(5),
            generalTcpFail(6),
            gcpKeepaliveTimeout(7),
            waitOperRetriesExceeded(8),
            initialConfigRetriesExceeded(9),
            auxCoreConfigFail(20)
    }
    MAX-ACCESS  read-only
    STATUS      current
    DESCRIPTION
        "The failure type in the result notification for the AUX core (TLV 86.8).
         Only meaningful if cerRpdAuxCoreStatusResult is set to failure."
    DEFVAL { none }
    ::= { cerRpdAuxCoreStatusEntry 5 }


--------------------------------------------------------------------------------------------------
-- RPHY DS Group to PW Multicast Address table
--------------------------------------------------------------------------------------------------

cerDsGrpToPwMcastAddrTable OBJECT-TYPE
    SYNTAX SEQUENCE OF CerDsGrpToPwMcastAddrEntry
    MAX-ACCESS not-accessible
    STATUS current
    DESCRIPTION
        "This table contains the mapping of a DS group to the MC address for the group.
         The MC address for the AllRpdDsRfPorts Group is not in this table, but rather
         in cerRphyAllRpdMcastIpAddr."
    ::= { cerRphyMib 49 }

cerDsGrpToPwMcastAddrEntry OBJECT-TYPE
    SYNTAX CerDsGrpToPwMcastAddrEntry
    MAX-ACCESS not-accessible
    STATUS current
    DESCRIPTION
        "An entry for the table."
    INDEX { cerDsGrpToPwMcastAddrRpdGrpName }
    ::= {cerDsGrpToPwMcastAddrTable 1}

CerDsGrpToPwMcastAddrEntry ::= SEQUENCE {
    cerDsGrpToPwMcastAddrRpdGrpName         DsVidGrpName,
    cerDsGrpToPwMcastAddrIpAddrType         InetAddressType,
    cerDsGrpToPwMcastAddrPwMcastIpAddr      InetAddressIPv4or6,
    cerDsGrpToPwMcastAddrRowStatus          RowStatus
}

cerDsGrpToPwMcastAddrRpdGrpName OBJECT-TYPE
    SYNTAX       DsVidGrpName
    MAX-ACCESS   not-accessible 
    STATUS       current
    DESCRIPTION
        "Name of the DS video RPD group."
    DEFVAL { "" }
    ::= {cerDsGrpToPwMcastAddrEntry 3}

cerDsGrpToPwMcastAddrIpAddrType OBJECT-TYPE
    SYNTAX InetAddressType
    MAX-ACCESS   read-create
    STATUS current
    DESCRIPTION
        "Type of the IP address; only IPv4 and IPv6 are allowed."
    ::= {cerDsGrpToPwMcastAddrEntry 1}

cerDsGrpToPwMcastAddrPwMcastIpAddr OBJECT-TYPE
    SYNTAX InetAddressIPv4or6
    MAX-ACCESS read-create
    STATUS current
    DESCRIPTION
        "The multicast IP address for transmitting this DS video PW."
    ::= {cerDsGrpToPwMcastAddrEntry 2}

cerDsGrpToPwMcastAddrRowStatus   OBJECT-TYPE
    SYNTAX      RowStatus
    MAX-ACCESS  read-create
    STATUS      current
    DESCRIPTION
        "The RowStatus for controlling entries in this table. 
         Allowed values are createAndGo, destroy, and active."
    ::= { cerDsGrpToPwMcastAddrEntry 4 }

--------------------------------------------------------------------------------------------------
-- RPD DS RF Port to FN Mapping table
--------------------------------------------------------------------------------------------------

cerDsRfPortFnTable OBJECT-TYPE
    SYNTAX SEQUENCE OF CerDsRfPortFnEntry
    MAX-ACCESS not-accessible
    STATUS current
    DESCRIPTION
        "This table contains the list of FNs assigned to a DS RPD RF port."
    ::= { cerRphyMib 50 }

cerDsRfPortFnEntry OBJECT-TYPE
    SYNTAX CerDsRfPortFnEntry
    MAX-ACCESS not-accessible
    STATUS current
    DESCRIPTION
        "An entry for the table."
    INDEX { cerDsRfPortFnRpdIndex, cerDsRfPortFnRpdPortId, cerDsRfPortFnFnName }
    ::= {cerDsRfPortFnTable 1}

CerDsRfPortFnEntry ::= SEQUENCE {
    cerDsRfPortFnRpdIndex                   CerRpdIndex,
    cerDsRfPortFnRpdPortId                  Unsigned32,
    cerDsRfPortFnFnName                     NodeName
}

cerDsRfPortFnRpdIndex OBJECT-TYPE
    SYNTAX CerRpdIndex
    MAX-ACCESS not-accessible
    STATUS current
    DESCRIPTION
        "The index of the RPD."
    ::= {cerDsRfPortFnEntry 1}

cerDsRfPortFnRpdPortId OBJECT-TYPE
    SYNTAX Unsigned32 (1..4)
    MAX-ACCESS not-accessible
    STATUS current
    DESCRIPTION
        "The RF port number on the RPD for this channel."
    ::= {cerDsRfPortFnEntry 2}

cerDsRfPortFnFnName OBJECT-TYPE
    SYNTAX NodeName
    MAX-ACCESS read-only
    STATUS current
    DESCRIPTION
        "Name of the Fiber node."
    ::= { cerDsRfPortFnEntry 3}

--------------------------------------------------------------------------------------------------
-- RPD DS RF Port to Video Group Mapping table
--------------------------------------------------------------------------------------------------

cerDsRfPortVideoTable OBJECT-TYPE
    SYNTAX SEQUENCE OF CerDsRfPortVideoEntry
    MAX-ACCESS not-accessible
    STATUS current
    DESCRIPTION
        "This table contains the list of video groups assigned to a DS RPD RF port."
    ::= { cerRphyMib 51 }

cerDsRfPortVideoEntry OBJECT-TYPE
    SYNTAX CerDsRfPortVideoEntry
    MAX-ACCESS not-accessible
    STATUS current
    DESCRIPTION
        "An entry for the table."
    INDEX { cerDsRfPortVideoRpdIndex, cerDsRfPortVideoRpdPortId, cerDsRfPortVideoGrpName }
    ::= {cerDsRfPortVideoTable 1}

CerDsRfPortVideoEntry ::= SEQUENCE {
    cerDsRfPortVideoRpdIndex                   CerRpdIndex,
    cerDsRfPortVideoRpdPortId                  Unsigned32,
    cerDsRfPortVideoGrpName                    DsVidGrpName
}

cerDsRfPortVideoRpdIndex OBJECT-TYPE
    SYNTAX CerRpdIndex
    MAX-ACCESS not-accessible
    STATUS current
    DESCRIPTION
        "The index of the RPD."
    ::= {cerDsRfPortVideoEntry 1}

cerDsRfPortVideoRpdPortId OBJECT-TYPE
    SYNTAX Unsigned32 (1..4)
    MAX-ACCESS not-accessible
    STATUS current
    DESCRIPTION
        "The RF port number on the RPD for this channel."
    ::= {cerDsRfPortVideoEntry 2}

cerDsRfPortVideoGrpName OBJECT-TYPE
    SYNTAX DsVidGrpName
    MAX-ACCESS read-only
    STATUS current
    DESCRIPTION
        "Name of the video group."
    ::= { cerDsRfPortVideoEntry 3}

--------------------------------------------------------------------------------------------------
-- RPD US RF Port to Fiber Node Mapping table
--------------------------------------------------------------------------------------------------

cerUsRfPortFnTable OBJECT-TYPE
    SYNTAX SEQUENCE OF CerUsRfPortFnEntry
    MAX-ACCESS not-accessible
    STATUS current
    DESCRIPTION
        "This table contains the list of FNs assigned to an US RF port."
    ::= { cerRphyMib 52 }

cerUsRfPortFnEntry OBJECT-TYPE
    SYNTAX CerUsRfPortFnEntry
    MAX-ACCESS not-accessible
    STATUS current
    DESCRIPTION
        "An entry for the table."
    INDEX { cerUsRfPortFnRpdIndex, cerUsRfPortFnRpdPortId, cerUsRfPortFnFnName }
    ::= {cerUsRfPortFnTable 1}

CerUsRfPortFnEntry ::= SEQUENCE {
    cerUsRfPortFnRpdIndex                   CerRpdIndex,
    cerUsRfPortFnRpdPortId                  Unsigned32,
    cerUsRfPortFnFnName                     NodeName
}

cerUsRfPortFnRpdIndex OBJECT-TYPE
    SYNTAX CerRpdIndex
    MAX-ACCESS not-accessible
    STATUS current
    DESCRIPTION
        "The index of the RPD."
    ::= {cerUsRfPortFnEntry 1}

cerUsRfPortFnRpdPortId OBJECT-TYPE
    SYNTAX Unsigned32 (1..4)
    MAX-ACCESS not-accessible
    STATUS current
    DESCRIPTION
        "The RF port number on the RPD for this channel."
    ::= {cerUsRfPortFnEntry 2}

cerUsRfPortFnFnName OBJECT-TYPE
    SYNTAX NodeName
    MAX-ACCESS read-only
    STATUS current
    DESCRIPTION
        "Name of the Fiber node."
    ::= { cerUsRfPortFnEntry 3 }

--------------------------------------------------------------------------------------------------
-- RPHY Traps
--------------------------------------------------------------------------------------------------

cerRphyTraps OBJECT IDENTIFIER
    ::= { cerRphyMib 70 0 }

cerRphyTrapsInfo OBJECT IDENTIFIER
    ::= { cerRphyMib 85 }

cerUnknownRpdMacAddr OBJECT-TYPE
    SYNTAX      MacAddress
    MAX-ACCESS  accessible-for-notify
    STATUS      current
    DESCRIPTION
        "The MAC Address of the unknown RPD trying to connect to the E6000 CER."
    ::= { cerRphyTrapsInfo 1 }

cerUnknownRpdIpAddr OBJECT-TYPE
    SYNTAX      InetAddressIPv4or6
    MAX-ACCESS  accessible-for-notify
    STATUS      current
    DESCRIPTION
        "The IP address of the unknown RPD trying to connect to the E6000 CER."
    ::= { cerRphyTrapsInfo 2 }

cerRphyAuxCoreFailure         NOTIFICATION-TYPE
    OBJECTS                  { trapCounter, trapSeverity, 
                               cerRpdIndexRpdIndex, cerRpdIndexRpdName,
                               cerRpdAuxCoreStatusAddrType,
                               cerRpdAuxCoreStatusIpAddr,
                               cerRpdAuxCoreStatusFailureType }
    STATUS                   current
    DESCRIPTION
         "This trap is sent when a configure auxiliary core fails on an
          In-service RPD."
    ::= { cerRphyTraps 1 }

cerRphyLocalConfigFileSaved NOTIFICATION-TYPE
    OBJECTS { trapCounter, trapSeverity }	
    STATUS current
    DESCRIPTION
    "This trap is sent when a 'write local-config-file' is executed on an RD2322, storing a local config file."
    ::= { cerRphyTraps 2 }

cerRphyLocalConfigFileErased NOTIFICATION-TYPE
    OBJECTS { trapCounter, trapSeverity}
    STATUS current
    DESCRIPTION
    "This trap is sent when an 'erase local-config-file' is executed on an RD2322, removing a local config file."
    ::= { cerRphyTraps 3 } 

cerRphyUnknownRpd NOTIFICATION-TYPE
    OBJECTS     { trapCounter, trapSeverity, 
                  cerUnknownRpdMacAddr, cerUnknownRpdIpAddr }
    STATUS      current
    DESCRIPTION
        "This trap is sent when an unconfigured RPD tries to connect to the E6000 CER."
    ::= { cerRphyTraps 4 }

--------------------------------------------------------------------------------------------------
-- E6000 Core RPD SSD CVC/CVC-CA Certs table
--------------------------------------------------------------------------------------------------
cerRpdSsdCvcTable OBJECT-TYPE
    SYNTAX SEQUENCE OF CerRpdSsdCvcEntry
    MAX-ACCESS not-accessible
    STATUS current
    DESCRIPTION
        "This table contains the R-PHY manufacturer and optionally MSO co-signer
         Code Verification Certificates (CVCs) and issuing CVC CA certificates.
         These certificates are passed to the RPDs to enable verification of 
         Secure Software Download (SSD) images."
    ::= { cerRphyMib 61 }

cerRpdSsdCvcEntry OBJECT-TYPE
    SYNTAX CerRpdSsdCvcEntry
    MAX-ACCESS not-accessible
    STATUS current
    DESCRIPTION
        "An entry for a manufacturer or co-signer CVC and it's issuing CVC-CA 
         certificate pair."
    INDEX { cerRpdSsdCvcIndex }
    ::= { cerRpdSsdCvcTable 1}

CerRpdSsdCvcEntry ::= SEQUENCE {
    cerRpdSsdCvcIndex             Integer32,
    cerRpdSsdCvcDescription       DisplayString,
    cerRpdSsdCvcSubject           SnmpAdminString,
    cerRpdSsdCvcIssuer            SnmpAdminString,
    cerRpdSsdCvcSerialNumber      SnmpAdminString,
    cerRpdSsdCvcCert              X509Certificate,
    cerRpdSsdCvcCaSubject         SnmpAdminString,
    cerRpdSsdCvcCaIssuer          SnmpAdminString,
    cerRpdSsdCvcCaSerialNumber    SnmpAdminString,
    cerRpdSsdCvcCaCert            X509Certificate,
    cerRpdSsdCvcStatus            RowStatus
}

cerRpdSsdCvcIndex OBJECT-TYPE
    SYNTAX           Integer32 (1..255)
    MAX-ACCESS       not-accessible
    STATUS           current
    DESCRIPTION
        "The type of a CCAP certificate."
    ::= { cerRpdSsdCvcEntry 1 }

cerRpdSsdCvcDescription OBJECT-TYPE
    SYNTAX           DisplayString
    MAX-ACCESS       read-create
    STATUS           current
    DESCRIPTION
        "An optional text description of the CVC/CVC-CA cert. "                 
    ::= { cerRpdSsdCvcEntry 2 }

cerRpdSsdCvcSubject OBJECT-TYPE
    SYNTAX           SnmpAdminString
    MAX-ACCESS       read-only
    STATUS           current
    DESCRIPTION
        "The subject name encoded in the x509 certificate,
         formatted as: /C=<country>/O=<Company Name>/CN=<FQDN> "                 
    ::= { cerRpdSsdCvcEntry 3 }

cerRpdSsdCvcIssuer OBJECT-TYPE
    SYNTAX           SnmpAdminString
    MAX-ACCESS       read-only
    STATUS           current
    DESCRIPTION
        "The subject name encoded in the x509 certificate,
         formatted as: /C=<country>/O=<Company Name>/OU=<CA identifier>/CN=<FQDN> "
    ::= { cerRpdSsdCvcEntry 4 }

cerRpdSsdCvcSerialNumber OBJECT-TYPE
    SYNTAX            SnmpAdminString
    MAX-ACCESS        read-only
    STATUS            current
    DESCRIPTION
        "This certificate's serial number represented as an asci string."
    ::= { cerRpdSsdCvcEntry 5 }

cerRpdSsdCvcCert  OBJECT-TYPE
    SYNTAX            X509Certificate
    MAX-ACCESS        read-create
    STATUS            current
    DESCRIPTION
        "The X509 DER-encoded CVC."    
    ::= { cerRpdSsdCvcEntry 6 }

cerRpdSsdCvcCaSubject OBJECT-TYPE
    SYNTAX           SnmpAdminString
    MAX-ACCESS       read-only
    STATUS           current
    DESCRIPTION
        "The subject name encoded in the x509 certificate,
         formatted as: /C=<country>/O=<Company Name>/OU=<CA identifier>/CN=<CA Name> "                 
    ::= { cerRpdSsdCvcEntry 7 }

cerRpdSsdCvcCaIssuer OBJECT-TYPE
    SYNTAX           SnmpAdminString
    MAX-ACCESS       read-only
    STATUS           current
    DESCRIPTION
        "The subject name encoded in the x509 certificate,
         formatted as: /C=<country>/O=<Company Name>/OU=<CA identifier>/CN=<CA Name> "
    ::= { cerRpdSsdCvcEntry 8 }

cerRpdSsdCvcCaSerialNumber OBJECT-TYPE
    SYNTAX            SnmpAdminString
    MAX-ACCESS        read-only
    STATUS            current
    DESCRIPTION
        "This CA certificate's serial number represented as an ascii string."
    ::= { cerRpdSsdCvcEntry 9 }

cerRpdSsdCvcCaCert OBJECT-TYPE
    SYNTAX            X509Certificate
    MAX-ACCESS        read-create
    STATUS            current
    DESCRIPTION
        "The X509 DER-encoded CVC CA certificate."    
    ::= { cerRpdSsdCvcEntry 10 }

cerRpdSsdCvcStatus OBJECT-TYPE
    SYNTAX      RowStatus
    MAX-ACCESS  read-create
    STATUS      current
    DESCRIPTION
        "The RowStatus for controlling entries in this table. 
         Allowed values are createAndGo, destroy, and active."
    ::= { cerRpdSsdCvcEntry 11 }

--------------------------------------------------------------------------------------------------
-- RPD Device Certs table
--------------------------------------------------------------------------------------------------

cerRpdDevCertTable OBJECT-TYPE
    SYNTAX SEQUENCE OF CerRpdDevCertEntry
    MAX-ACCESS not-accessible
    STATUS current
    DESCRIPTION
        "This table contains the RPD device certificates."
    ::= { cerRphyMib 62 }

cerRpdDevCertEntry OBJECT-TYPE
    SYNTAX CerRpdDevCertEntry
    MAX-ACCESS not-accessible
    STATUS current
    DESCRIPTION
        "An entry for one RPD device certificate."
    INDEX { cerRpdDevCertRpdIndex }
    ::= {cerRpdDevCertTable 1}

CerRpdDevCertEntry ::= SEQUENCE {
    cerRpdDevCertRpdIndex             CerRpdIndex,
    cerRpdDevCert509Cert              X509Certificate,
    cerRpdDevCertIssuerCaCertIndex    Integer32,
    cerRpdDevCertRowStatus            RowStatus
}
cerRpdDevCertRpdIndex OBJECT-TYPE
    SYNTAX CerRpdIndex 
    MAX-ACCESS not-accessible
    STATUS current
    DESCRIPTION
        "RPD global index used in the RPD."
    ::= { cerRpdDevCertEntry 1}

cerRpdDevCert509Cert	OBJECT-TYPE
    SYNTAX  	        X509Certificate
    MAX-ACCESS 	read-create
    STATUS  	        current
    DESCRIPTION
        "The X509 DER-encoded RPD device certificate."    
    REFERENCE
         "DOCSIS Baseline Privacy Plus Interface Specification,
          Section 9.2."
    ::= { cerRpdDevCertEntry 2 }
cerRpdDevCertIssuerCaCertIndex OBJECT-TYPE
    SYNTAX  	Integer32 (101..200)
    MAX-ACCESS read-create
    STATUS  	current
    DESCRIPTION
	"The index into the docsBpi2CmtsCACertTable for the issuer CA certificate. Must be set."
    ::= { cerRpdDevCertEntry 3 }

cerRpdDevCertRowStatus   OBJECT-TYPE
    SYNTAX      RowStatus
    MAX-ACCESS  read-create
    STATUS      current
    DESCRIPTION
        "The RowStatus for controlling entries in this table. 
         Allowed values are createAndGo, destroy, and active."
    ::= { cerRpdDevCertEntry 4 }

--------------------------------------------------------------------------------------------------
-- RPD SSD table
--------------------------------------------------------------------------------------------------

cerRpdSsdTable OBJECT-TYPE
    SYNTAX SEQUENCE OF CerRpdSsdEntry
    MAX-ACCESS not-accessible
    STATUS current
    DESCRIPTION
        "This table information needed to do SSD to an RPD."
    ::= { cerRphyMib 63 }

cerRpdSsdEntry OBJECT-TYPE
    SYNTAX CerRpdSsdEntry
    MAX-ACCESS not-accessible
    STATUS current
    DESCRIPTION
        "An entry for one software load."
    INDEX { cerRpdSsdVendorId, cerRpdSsdModel }
    ::= {cerRpdSsdTable 1}

CerRpdSsdEntry ::= SEQUENCE {
    cerRpdSsdVendorId             Unsigned32,
    cerRpdSsdModel                DisplayString,         
    cerRpdSsdFileName             DisplayString,
    cerRpdSsdAddrType             InetAddressType,
    cerRpdSsdServerAddr           InetAddress,
    cerRpdSsdServerIpAddr         InetAddressIPv4or6,
    cerRpdSsdTransportType        INTEGER,
    cerRpdSsdManufCvcIndex        Integer32,
    cerRpdSsdCosignerCvcIndex     Integer32,
    cerRpdSsdEnabled              TruthValue,
    cerRpdSsdRowStatus            RowStatus
}

cerRpdSsdVendorId OBJECT-TYPE
        SYNTAX       Unsigned32 (0..65535)
        MAX-ACCESS  not-accessible
        STATUS      current
        DESCRIPTION
            "RPD manufacturer's vendor id as the IANA-assigned 
             'SMI Network Management Private Enterprise Codes' value."
        ::= { cerRpdSsdEntry 1 }

cerRpdSsdModel OBJECT-TYPE
        SYNTAX      DisplayString (SIZE(1..255))
        MAX-ACCESS  not-accessible
        STATUS      current
        DESCRIPTION
            "The software model of the RPD that would use this software load.
             If there is no row in the cerRpdHwToSwModelTable for this vendor
             and an RPD hardware model, this is that RPD hardware model number.
             The keyword 'any' matches all model values for a particular vendor,
             but at a lower precedence than an exact match of the model string."
        ::= { cerRpdSsdEntry 2 }

cerRpdSsdFileName OBJECT-TYPE
        SYNTAX      DisplayString (SIZE(1..255))
        MAX-ACCESS  read-create
        STATUS      current
        DESCRIPTION
            "The file name for this software load. "
        ::= { cerRpdSsdEntry 3 }

cerRpdSsdAddrType OBJECT-TYPE
    SYNTAX InetAddressType
    MAX-ACCESS read-create
    STATUS current
    DESCRIPTION
        "Type of the RPD IP address (DNS, IPv4, IPv6)."
    DEFVAL { ipv6 }
    ::= {cerRpdSsdEntry 4}

cerRpdSsdServerAddr OBJECT-TYPE
    SYNTAX InetAddress
    MAX-ACCESS read-create
    STATUS current
    DESCRIPTION
        "The address of the file server for the SW file: IPv4 or IPv6."
    DEFVAL { ""  }
    ::= {cerRpdSsdEntry 5}

cerRpdSsdServerIpAddr OBJECT-TYPE
    SYNTAX InetAddressIPv4or6
    MAX-ACCESS read-create
    STATUS current
    DESCRIPTION
        "The IP address of the file server for the SW file.
         This is the empty string if type
         is DNS, and URL cannot be resolved. Same value as
         cerRpdSsdServerAddr if type is not DNS."
    DEFVAL { ""  }
    ::= {cerRpdSsdEntry 6}

cerRpdSsdTransportType OBJECT-TYPE
    SYNTAX INTEGER {
            tftp(1),
            http(2)
    }
    MAX-ACCESS      read-create
    STATUS          current
    DESCRIPTION
        "The file transport method for the software download." 
    DEFVAL { tftp }
    ::= {cerRpdSsdEntry 7}

cerRpdSsdManufCvcIndex OBJECT-TYPE
    SYNTAX    Integer32 (0..255)
    MAX-ACCESS read-create
    STATUS    current
    DESCRIPTION
       "The index into the cerRpdSsdCvcTable for the manufacturer CVC. 
        Must be set to a non-zero value before cerRpdSsdEnabled can be set to true."
    DEFVAL { 0 }
    ::= { cerRpdSsdEntry 8}

cerRpdSsdCosignerCvcIndex OBJECT-TYPE
    SYNTAX  	Integer32 (0|1..255)
    MAX-ACCESS read-create
    STATUS  	current
    DESCRIPTION
        "The index into the cerRpdSsdCvcTable for the cosigner CVC. Zero if no cosigner."
    DEFVAL { 0 }
    ::= { cerRpdSsdEntry 9 }

cerRpdSsdEnabled OBJECT-TYPE
    SYNTAX       TruthValue
    MAX-ACCESS   read-create
    STATUS       current
    DESCRIPTION 
	   "Set to true when the RPD SSD entry is enabled, false otherwise."
    DEFVAL { false }
    ::= { cerRpdSsdEntry 10 }

cerRpdSsdRowStatus   OBJECT-TYPE
    SYNTAX      RowStatus
    MAX-ACCESS  read-create
    STATUS      current
    DESCRIPTION
        "The RowStatus for controlling entries in this table. 
         Allowed values are createAndGo, destroy, and active."
    ::= { cerRpdSsdEntry 11 }


--------------------------------------------------------------------------------------------------
-- RPD Hardware To Software Model Number table
--------------------------------------------------------------------------------------------------

cerRpdHwToSwModelTable OBJECT-TYPE
    SYNTAX SEQUENCE OF CerRpdHwToSwModelEntry
    MAX-ACCESS not-accessible
    STATUS current
    DESCRIPTION
        "This table has RPD hardware model numbers that all share a software load
         mapping to a common software model number. If there is only one hardware
         model number for a supported RPD, that HW model number may be used directly in 
         the cerRpdSsdTable in place of a software model number, with no corresponding row
         in this table."
    ::= { cerRphyMib 64 }

cerRpdHwToSwModelEntry OBJECT-TYPE
    SYNTAX CerRpdHwToSwModelEntry
    MAX-ACCESS not-accessible
    STATUS current
    DESCRIPTION
        "An entry for mapping one HW model to one SW model number."
    INDEX { cerRpdHwToSwModelVendorId, cerRpdHwToSwModelHwModelNum }
    ::= {cerRpdHwToSwModelTable 1}

CerRpdHwToSwModelEntry ::= SEQUENCE {
    cerRpdHwToSwModelVendorId                OCTET STRING,
    cerRpdHwToSwModelHwModelNum              DisplayString,
    cerRpdHwToSwModelSwModelNum              DisplayString,
    cerRpdHwToSwModelRowStatus               RowStatus
}

cerRpdHwToSwModelVendorId OBJECT-TYPE
    SYNTAX      OCTET STRING (SIZE(2)) 
    MAX-ACCESS  not-accessible
    STATUS      current
    DESCRIPTION
        "The vendor Id of the RPD that would use this software load. "
    ::= { cerRpdHwToSwModelEntry 1 }

cerRpdHwToSwModelHwModelNum OBJECT-TYPE
    SYNTAX      DisplayString (SIZE(1..255))
    MAX-ACCESS  not-accessible
    STATUS      current
    DESCRIPTION
        "The hardware model (cerRpdDataPartModelNum) of an RPD that. "
    ::= { cerRpdHwToSwModelEntry 2 }

cerRpdHwToSwModelSwModelNum OBJECT-TYPE
    SYNTAX      DisplayString (SIZE(1..32))
    MAX-ACCESS  read-create
    STATUS      current
    DESCRIPTION
        "The software model for identifying the software load that an RPD would use. "
    ::= { cerRpdHwToSwModelEntry 3 }

cerRpdHwToSwModelRowStatus   OBJECT-TYPE
    SYNTAX      RowStatus
    MAX-ACCESS  read-create
    STATUS      current
    DESCRIPTION
        "The RowStatus for controlling entries in this table. 
         Allowed values are createAndGo, destroy, and active."
    ::= { cerRpdHwToSwModelEntry 4 }
    
--------------------------------------------------------------------------------------------------
-- Video DS Group to Mac channel table
--------------------------------------------------------------------------------------------------

cerDsGrpToCoreChanTable OBJECT-TYPE
    SYNTAX SEQUENCE OF CerDsGrpToCoreChanEntry
    MAX-ACCESS not-accessible
    STATUS current
    DESCRIPTION
        "This table contains the list of core mac channels assigned to a video ds-group."
    ::= { cerRphyMib 65 }

cerDsGrpToCoreChanEntry OBJECT-TYPE
    SYNTAX CerDsGrpToCoreChanEntry
    MAX-ACCESS not-accessible
    STATUS current
    DESCRIPTION
        "An entry for the table."
    INDEX { cerDsGrpToCoreChanRpdGrpName, cerDsGrpToCoreChanIfIndex }
    ::= {cerDsGrpToCoreChanTable 1}

CerDsGrpToCoreChanEntry ::= SEQUENCE {
    cerDsGrpToCoreChanRpdGrpName         DsVidGrpName,
    cerDsGrpToCoreChanIfIndex            InterfaceIndex
}

cerDsGrpToCoreChanRpdGrpName OBJECT-TYPE
    SYNTAX DsVidGrpName
    MAX-ACCESS not-accessible
    STATUS current
    DESCRIPTION
        "Name of the DS video RPD group."
    ::= { cerDsGrpToCoreChanEntry 1}

cerDsGrpToCoreChanIfIndex OBJECT-TYPE
    SYNTAX InterfaceIndex
    MAX-ACCESS read-only
    STATUS current
    DESCRIPTION
        "IfIndex of the MAC channel in the ds-group."
    ::= { cerDsGrpToCoreChanEntry 2}

--========================= cerRpdDsPowerFineAdjTable =========================

cerRpdDsPowerFineAdjTable OBJECT-TYPE
    SYNTAX      SEQUENCE OF CerRpdDsPowerFineAdjEntry
    MAX-ACCESS  not-accessible
    STATUS      current
    DESCRIPTION
        "This status table contains the fine power adjustment for SC-QAM and OFDM channels."
    ::= { cerRphyMib 66 }

cerRpdDsPowerFineAdjEntry OBJECT-TYPE
    SYNTAX      CerRpdDsPowerFineAdjEntry
    MAX-ACCESS  not-accessible
    STATUS      current
    DESCRIPTION
        "An entry contains one RPD SC-QAM channel."
    INDEX { cerRpdDsPowerFineAdjRpdIndex, cerRpdDsPowerFineAdjRpdChanIfIndex }
    ::= { cerRpdDsPowerFineAdjTable 1 }

CerRpdDsPowerFineAdjEntry ::= SEQUENCE {
        cerRpdDsPowerFineAdjRpdIndex            CerRpdIndex,
        cerRpdDsPowerFineAdjRpdChanIfIndex      InterfaceIndex,
        cerRpdDsPowerFineAdjDelta               Integer32,
        cerRpdDsPowerFineAdjRowStatus           RowStatus
    }

cerRpdDsPowerFineAdjRpdIndex OBJECT-TYPE
    SYNTAX CerRpdIndex
    MAX-ACCESS not-accessible
    STATUS current
    DESCRIPTION
        "The index of the RPD."
    ::= { cerRpdDsPowerFineAdjEntry 1}

cerRpdDsPowerFineAdjRpdChanIfIndex OBJECT-TYPE
    SYNTAX     InterfaceIndex
    MAX-ACCESS not-accessible
    STATUS     current
    DESCRIPTION
        "The PHY channel ifIndex of this downstream SC-QAM or OFDM channel."
    ::= { cerRpdDsPowerFineAdjEntry 2 }

cerRpdDsPowerFineAdjDelta OBJECT-TYPE
    SYNTAX      Integer32 (-80..0)
    UNITS       "Steps"
    MAX-ACCESS  read-create
    STATUS      current
    DESCRIPTION
        "Total power is sum of base power, tilt factor, and the fine
         power adjustment delta. Sent in TLV 62.16 for an SC-QAM channel 
         or 63.14 for an OFDM channel"
    DEFVAL { 0 }
    ::= { cerRpdDsPowerFineAdjEntry 3 }

cerRpdDsPowerFineAdjRowStatus OBJECT-TYPE
    SYNTAX      RowStatus
    MAX-ACCESS  read-create
    STATUS      current
    DESCRIPTION
        "The RowStatus for controlling entries in this table. 
         Allowed values are createAndGo, destroy, and active."
    ::= { cerRpdDsPowerFineAdjEntry 4 }


--========================= cerRpdShelfTable =========================

cerRpdShelfTable OBJECT-TYPE
    SYNTAX      SEQUENCE OF CerRpdShelfEntry
    MAX-ACCESS  not-accessible
    STATUS      current
    DESCRIPTION
        "This status table contains the RPDs in a shelf."
    ::= { cerRphyMib 67 }

cerRpdShelfEntry OBJECT-TYPE
    SYNTAX      CerRpdShelfEntry
    MAX-ACCESS  not-accessible
    STATUS      current
    DESCRIPTION
        "An entry contains one RPD in the shelf."
    INDEX { cerRpdShelfSerialNumber, cerRpdShelfRpdIndex}
    ::= { cerRpdShelfTable 1 }

CerRpdShelfEntry ::= SEQUENCE {
        cerRpdShelfSerialNumber        SnmpAdminString,
        cerRpdShelfRpdIndex            CerRpdIndex,
        cerRpdShelfEntityIndex         Integer32,
        cerRpdShelfSlot                Integer32
    }

cerRpdShelfSerialNumber OBJECT-TYPE
    SYNTAX     SnmpAdminString
    MAX-ACCESS not-accessible
    STATUS     current
    DESCRIPTION
        "The serial number returned by the RPD in TLV 100.6.11 for 
         Class equal chassis(3) in TLV 100.6.5."
    ::= { cerRpdShelfEntry 1 }

cerRpdShelfRpdIndex OBJECT-TYPE
    SYNTAX CerRpdIndex
    MAX-ACCESS not-accessible
    STATUS current
    DESCRIPTION
        "The RPD index."
    ::= { cerRpdShelfEntry 2}

cerRpdShelfEntityIndex OBJECT-TYPE
    SYNTAX      Integer32
    MAX-ACCESS  read-only
    STATUS      current
    DESCRIPTION
        "The Entity index from TLV 100.6.1 when class (TLV 100.6.5) equal chassis(3)."
    DEFVAL { 0 }
    ::= { cerRpdShelfEntry 3 }

cerRpdShelfSlot OBJECT-TYPE
    SYNTAX      Integer32
    MAX-ACCESS  read-only
    STATUS      current
    DESCRIPTION
        "The RPD slot number. This is the ParentRelPos (TLV 100.6.6) from the Entity 
        Instance where class (TLV 100.6.5) equals container(5) and whose ContainedIn 
        Value (TLV 100.6.4) value equals cerRpdShelfEntityIndex (i.e., equals the chassis instance)."
    DEFVAL { 0 }
    ::= { cerRpdShelfEntry 4 }

--------------------------------------------------------------------------------------------------
-- NDF/NDR Channel tables
--------------------------------------------------------------------------------------------------

cerOobNdfDsChanTable OBJECT-TYPE
    SYNTAX SEQUENCE OF CerOobNdfDsChanEntry
    MAX-ACCESS not-accessible
    STATUS current
    DESCRIPTION
        "This table contains the OOB 55-1 DS channels."
    ::= { cerRphyMib 68 }

cerOobNdfDsChanEntry OBJECT-TYPE
    SYNTAX CerOobNdfDsChanEntry
    MAX-ACCESS not-accessible
    STATUS current
    DESCRIPTION
        "An entry for the table."
    INDEX { cerOobNdfDsChanIfIndex }
    ::= {cerOobNdfDsChanTable 1}

CerOobNdfDsChanEntry ::= SEQUENCE {
    cerOobNdfDsChanIfIndex           InterfaceIndex,
    cerOobNdfDsChanRpdGrpName        DsVidGrpName,
    cerOobNdfDsChanCenterFreq        Unsigned32,
    cerOobNdfDsChanWidth             Unsigned32,
    cerOobNdfDsChanSrcIpAddrType     InetAddressType,
    cerOobNdfDsChanSrcIpAddr         InetAddressIPv4or6,
    cerOobNdfDsChanPowerAdj          TenthdB,
    cerOobNdfDsChanDataPwId          Unsigned32,
    cerOobNdfDsChanChanSelector      Unsigned32
}

cerOobNdfDsChanIfIndex OBJECT-TYPE
    SYNTAX InterfaceIndex 
    MAX-ACCESS not-accessible
    STATUS current
    DESCRIPTION
        "The E6000 ifIndex of the DS MAC NDF channel."
    ::= { cerOobNdfDsChanEntry 1}

cerOobNdfDsChanRpdGrpName OBJECT-TYPE
    SYNTAX DsVidGrpName
    MAX-ACCESS read-write
    STATUS current
    DESCRIPTION
        "Name of the DS video RPD group for this OOB NDF DS channel."
    DEFVAL { "" }
    ::= { cerOobNdfDsChanEntry 2}

cerOobNdfDsChanCenterFreq OBJECT-TYPE
    SYNTAX      Unsigned32 (0|50000000..1000000000)
    UNITS       "Hertz"
    MAX-ACCESS read-write
    STATUS current
    DESCRIPTION
        "Center Frequency of this OOB NDF DS channel. 25 KHz granularity."
    DEFVAL { 0 }
    ::= { cerOobNdfDsChanEntry 3}

cerOobNdfDsChanWidth OBJECT-TYPE
    SYNTAX      Unsigned32 (80000|160000|320000|640000|1280000|2560000|5120000|25600000)
    UNITS       "Hertz"
    MAX-ACCESS read-write
    STATUS current
    DESCRIPTION
        "Channel width of this OOB NDF DS channel.  R-OOB spec defines values: 80kHz, 160 kHz,
        320 kHz, 640 kHz, 1.28MHz, 2.56MHz, 5.12MHz, and 25.6MHz."
    DEFVAL { 2560000 }
    ::= { cerOobNdfDsChanEntry 4}

cerOobNdfDsChanSrcIpAddrType OBJECT-TYPE
    SYNTAX InetAddressType
    MAX-ACCESS   read-write
    STATUS current
    DESCRIPTION
        "Type of engine address (ipv4 or ipv6)."
    DEFVAL { ipv6 }
    ::= { cerOobNdfDsChanEntry 5}

cerOobNdfDsChanSrcIpAddr OBJECT-TYPE
    SYNTAX InetAddressIPv4or6
    MAX-ACCESS read-write
    STATUS current
    DESCRIPTION
        "The OOB NDF engine IP source address for incoming DS OOB NDF packets to this channel.
         Address is zero if any-source multicast is used."
    DEFVAL { '00000000000000000000000000000000'H }
    ::= { cerOobNdfDsChanEntry 6}

cerOobNdfDsChanPowerAdj OBJECT-TYPE
    SYNTAX TenthdB (0|-200..-30)
    UNITS "TenthdB"
    MAX-ACCESS read-write
    STATUS current
    DESCRIPTION
        "Power adjustment (reduction relative to base power) for this OOB NDF DS channel."
     DEFVAL { 0 }
    ::= { cerOobNdfDsChanEntry 7}
    
cerOobNdfDsChanDataPwId OBJECT-TYPE
    SYNTAX Unsigned32 (0|2147483649..2147549183)
    MAX-ACCESS read-write
    STATUS current
    DESCRIPTION
        "The Session ID of the data pseudowire carrying the OOB NDF
         channel. Assigned by Core configuring this channel. Must be
         in multicast session ID range: 0x80000001..0x8000FFFF"
    DEFVAL { 0 }
    ::= { cerOobNdfDsChanEntry 8 }

cerOobNdfDsChanChanSelector OBJECT-TYPE
    SYNTAX Unsigned32
    MAX-ACCESS   read-only
    STATUS current
    DESCRIPTION
        "DEPI channel selector for this DS OOB channel on the RPD. This 24 bit number
         has the RPD RF port number in the upper 8 bits, the channel type in
         the middle 8 bits, and the channel index in low 8 bits.
         For NDF, the channel type valie is 10 (0xA)."
    REFERENCE
        "DEPI Table 9"
    ::= { cerOobNdfDsChanEntry 9}


cerOobNdrUsChanTable OBJECT-TYPE
    SYNTAX SEQUENCE OF CerOobNdrUsChanEntry
    MAX-ACCESS not-accessible
    STATUS current
    DESCRIPTION
        "This table contains the OOB NDR US channels."
    ::= { cerRphyMib 69 }

cerOobNdrUsChanEntry OBJECT-TYPE
    SYNTAX CerOobNdrUsChanEntry
    MAX-ACCESS not-accessible
    STATUS current
    DESCRIPTION
        "An entry for the table."
    INDEX { cerOobNdrUsChanIfIndex }
    ::= {cerOobNdrUsChanTable 1}

CerOobNdrUsChanEntry ::= SEQUENCE {
    cerOobNdrUsChanIfIndex           InterfaceIndex,
    cerOobNdrUsChanRpdGrpName        DsVidGrpName,
    cerOobNdrUsChanCenterFreq        Unsigned32,
    cerOobNdrUsChanWidth             Unsigned32,
    cerOobNdrUsChanDstIpAddrType     InetAddressType,
    cerOobNdrUsChanDstIpAddr         InetAddressIPv4or6,
    cerOobNdrUsChanDscp              Unsigned32,
    cerOobNdrUsChanPowerTgt          TenthdB,
    cerOobNdrUsChanDataPwId          Unsigned32,
    cerOobNdrUsChanChanSelector      Unsigned32,
    cerOobNdrUsChanSrcIpAddrType     InetAddressType,
    cerOobNdrUsChanSrcIpAddr         InetAddressIPv4or6
}

cerOobNdrUsChanIfIndex OBJECT-TYPE
    SYNTAX InterfaceIndex 
    MAX-ACCESS not-accessible
    STATUS current
    DESCRIPTION
        "The E6000 ifIndex of the US MAC NDF channel."
    ::= { cerOobNdrUsChanEntry 1}

cerOobNdrUsChanRpdGrpName OBJECT-TYPE
    SYNTAX DsVidGrpName
    MAX-ACCESS read-write
    STATUS current
    DESCRIPTION
        "Name of the US RPD group for this OOB NDF DS channel."
    DEFVAL { "" }
    ::= { cerOobNdrUsChanEntry 2}

cerOobNdrUsChanCenterFreq OBJECT-TYPE
    SYNTAX      Unsigned32 (0|5000000..65000000)
    UNITS       "Hertz"
    MAX-ACCESS read-write
    STATUS current
    DESCRIPTION
        "Center Frequency of this OOB NDR US channel. Range is 5 to 42 MHz."
    DEFVAL { 0 }
    ::= { cerOobNdrUsChanEntry 3}

cerOobNdrUsChanWidth OBJECT-TYPE
    SYNTAX      Unsigned32 (160000|320000|640000|1280000|2560000|5120000)
    UNITS       "Hertz"
    MAX-ACCESS read-write
    STATUS current
    DESCRIPTION
        "Channel width of this OOB NDR US channel.  R-OOB spec defines values: 160 kHz,
        320 kHz, 640 kHz, 1.28MHz, 2.56MHz, and 5.12MHz."
    DEFVAL { 2560000 }
    ::= { cerOobNdrUsChanEntry 4}

cerOobNdrUsChanDstIpAddrType OBJECT-TYPE
    SYNTAX InetAddressType
    MAX-ACCESS   read-write
    STATUS current
    DESCRIPTION
        "Type of engine address (ipv4 or ipv6)."
    DEFVAL { ipv6 }
    ::= { cerOobNdrUsChanEntry 5}

cerOobNdrUsChanDstIpAddr OBJECT-TYPE
    SYNTAX InetAddressIPv4or6
    MAX-ACCESS read-write
    STATUS current
    DESCRIPTION
        "The OOB NDR engine IP destination address for incoming US OOB NDR packets to this channel."
    DEFVAL { '00000000000000000000000000000000'H }
    ::= { cerOobNdrUsChanEntry 6}

cerOobNdrUsChanDscp OBJECT-TYPE
    SYNTAX Unsigned32
    MAX-ACCESS   read-write
    STATUS current
    DESCRIPTION
        "6 LSB carry per Hop Behavior Identifier.  That equals the 6-bit DSCP with 
         which the RPD transmits L2TPv3 data packets on the return direction static
         psuedowire.  The upper two bits are set as '00' byt eh Core and ignored by
         the RPD.  The default is 0 (best effort)."
    DEFVAL { 0 }
    ::= { cerOobNdrUsChanEntry 7}

cerOobNdrUsChanPowerTgt OBJECT-TYPE
    SYNTAX TenthdB (-100..100)
    UNITS "TenthdB"
    MAX-ACCESS read-write
    STATUS current
    DESCRIPTION
        "Target received power adjustment for this OOB NDR US channel."
     DEFVAL { 0 }
    ::= { cerOobNdrUsChanEntry 8}

cerOobNdrUsChanDataPwId OBJECT-TYPE
    SYNTAX          Unsigned32 (0|1..4294967295)
    MAX-ACCESS      read-write
    STATUS          current
    DESCRIPTION
        "The Core UEPI Session ID of the data pseudo-wire carrying the OOB NDR channel.
         Assigned by the the Core configuring the channel on the RPD."
    DEFVAL { 0 }
    ::= { cerOobNdrUsChanEntry 9}

cerOobNdrUsChanChanSelector OBJECT-TYPE
    SYNTAX Unsigned32
    MAX-ACCESS   read-only
    STATUS current
    DESCRIPTION
        "UEPI channel selector for this US OOB channel on the RPD. This 24 bit number
         has the RPD RF port number in the upper 8 bits, the channel type in
         the middle 8 bits, and the channel index in low 8 bits.
         For NDR, the channel type valie is 11 (0xB)."
    REFERENCE
        "UEPI Table 9"
    ::= { cerOobNdrUsChanEntry 10}
    
cerOobNdrUsChanSrcIpAddrType OBJECT-TYPE
    SYNTAX InetAddressType
    MAX-ACCESS   read-only
    STATUS current
    DESCRIPTION
        "Type of RPD source address."
    DEFVAL { ipv6 }
    ::= { cerOobNdrUsChanEntry 11}

cerOobNdrUsChanSrcIpAddr OBJECT-TYPE
    SYNTAX InetAddressIPv4or6
    MAX-ACCESS read-only
    STATUS current
    DESCRIPTION
        "The RPD source IP address for outgoing OOB NDR packets to this channel."
    DEFVAL { '00000000000000000000000000000000'H }
    ::= { cerOobNdrUsChanEntry 12}

--------------------------------------------------------------------------------------------------
-- LAG/Daisy Chain tables
--------------------------------------------------------------------------------------------------
cerRpdAdpLldpPortStatusTable        OBJECT-TYPE
    SYNTAX      SEQUENCE OF CerRpdAdpLldpPortStatusEntry
    MAX-ACCESS  not-accessible
    STATUS      current
    DESCRIPTION
        "This table reports status of ARRIS Discovery Protocol (ADP) 
         and LLDP per Ethernet port parameters on the RPD."
    REFERENCE
        "E6000 CER R8.0/E6000n R-PHY R1.3 Support for 
         Ring/Daisy Chain Configurations PSA."
    ::= { cerRphyMib 71 }

cerRpdAdpLldpPortStatusEntry        OBJECT-TYPE
    SYNTAX      CerRpdAdpLldpPortStatusEntry
    MAX-ACCESS  not-accessible
    STATUS      current
    DESCRIPTION
        "An entry containing status information
         applicable to ADP and LLDP on a particular RPD."
    INDEX { cerRpdAdpLldpPortStatusRpdIndex,
            cerRpdAdpLldpPortStatusEnetPortNum }
    ::= { cerRpdAdpLldpPortStatusTable 1 }

CerRpdAdpLldpPortStatusEntry ::=
    SEQUENCE {
        cerRpdAdpLldpPortStatusRpdIndex           CerRpdIndex,
        cerRpdAdpLldpPortStatusEnetPortNum        Unsigned32,
        cerRpdAdpLldpPortStatusAdpState           INTEGER,
        cerRpdAdpLldpPortStatusAdpHopCnt          Unsigned32,
        cerRpdAdpLldpPortStatusNbrMacAddr         MacAddress,
        cerRpdAdpLldpPortStatusChassisSubType     INTEGER,
        cerRpdAdpLldpPortStatusChassisId          OCTET STRING,
        cerRpdAdpLldpPortStatusPortSubType        INTEGER,
        cerRpdAdpLldpPortStatusPortId             OCTET STRING
    }

cerRpdAdpLldpPortStatusRpdIndex OBJECT-TYPE
    SYNTAX      CerRpdIndex
    MAX-ACCESS  not-accessible
    STATUS      current
    DESCRIPTION
        "The RPD ifIndex of the Ethernet port."
    ::= { cerRpdAdpLldpPortStatusEntry 1 }

cerRpdAdpLldpPortStatusEnetPortNum OBJECT-TYPE
    SYNTAX      Unsigned32
    MAX-ACCESS  not-accessible
    STATUS      current
    DESCRIPTION
        "The Ethernet port number on the RPD."
    ::= { cerRpdAdpLldpPortStatusEntry 2 }

cerRpdAdpLldpPortStatusAdpState OBJECT-TYPE
    SYNTAX      INTEGER {
        unknown (0),
        initialized (1),
        holddown (2),
        waitfornbr (3),
        uplink (4),
        downlink (5)
    }
    MAX-ACCESS  read-only
    STATUS      current
    DESCRIPTION
        "The current state of the ADP state machine for the Ethernet port on the RPD.
         This is populated using vendor-specific TLV 21.4.8.2"
    ::= { cerRpdAdpLldpPortStatusEntry 3 }

cerRpdAdpLldpPortStatusAdpHopCnt OBJECT-TYPE
    SYNTAX      Unsigned32 (0..255)
    MAX-ACCESS  read-only
    STATUS      current
    DESCRIPTION
        "The current value of the ADP Hop Count parameter for the Ethernet port on the RPD.
         This is populated using vendor-specific TLV 21.4.8.3"
    ::= { cerRpdAdpLldpPortStatusEntry 4 }

cerRpdAdpLldpPortStatusNbrMacAddr OBJECT-TYPE
    SYNTAX      MacAddress
    MAX-ACCESS  read-only
    STATUS      current
    DESCRIPTION
        "The MAC Address sent by the neighboring node via LLDP.
         This is populated using vendor-specific TLV 21.5.2"
    ::= { cerRpdAdpLldpPortStatusEntry 5 }
    
cerRpdAdpLldpPortStatusChassisSubType OBJECT-TYPE
    SYNTAX      INTEGER {
        unknown (0),
        chassisComponent (1),
        interfaceAlias (2),
        portComponent (3),
        macAddress (4),
        networkAddress (5),
        interfaceName (6),
        locallyAssigned (7)
    }
    MAX-ACCESS  read-only
    STATUS      current
    DESCRIPTION
        "The Chassis Subtype identification sent by the neighboring node.
         This is populated using vendor-specific TLV 21.5.3.
         The RPD reports macAddress(4) as its Chassis Subtype.
         If a connected CIN device supports LLDP, it may report one of
         the other Chassis Subtype values as defined by 802.1AB."
    ::= { cerRpdAdpLldpPortStatusEntry 6 }

cerRpdAdpLldpPortStatusChassisId OBJECT-TYPE
    SYNTAX      OCTET STRING (SIZE(0..255))
    MAX-ACCESS  read-only
    STATUS      current
    DESCRIPTION
        "The Chassis ID value sent by the neighboring node.
         This is populated using vendor-specific TLV 21.5.4.
         For an RPD, this attribute contains a MAC address."
    ::= { cerRpdAdpLldpPortStatusEntry 7 }

cerRpdAdpLldpPortStatusPortSubType OBJECT-TYPE
    SYNTAX      INTEGER {
        unknown (0),
        interfaceAlias (1),
        portComponent (2),
        macAddress (3),
        networkAddress (4),
        interfaceName (5),
        agentCircuitId (6),
        locallyAssigned (7)
    }
    MAX-ACCESS  read-only
    STATUS      current
    DESCRIPTION
        "The Port Subtype identification sent by the neighboring node.
         This is populated using vendor-specific TLV 21.5.5.
         The RPD reports locallyAssigned(7) as its Port Subtype.
         If a connected CIN device supports LLDP, it may report one of
         the other Port Subtype values as defined by 802.1AB."
    ::= { cerRpdAdpLldpPortStatusEntry 8 }

cerRpdAdpLldpPortStatusPortId OBJECT-TYPE
    SYNTAX      OCTET STRING (SIZE(0..255))
    MAX-ACCESS  read-only
    STATUS      current
    DESCRIPTION
        "The Port ID value sent by the neighboring node.
         This is populated using vendor-specific TLV 21.5.6.
         For an RPD, this attribute contains an Ethernet port number."
    ::= { cerRpdAdpLldpPortStatusEntry 9 }

--------------------------------------------------------------------------------------------------
-- RPD Ethernet Diagnostics table
--------------------------------------------------------------------------------------------------

cerRpdEnetDiagsTable OBJECT-TYPE
    SYNTAX SEQUENCE OF CerRpdEnetDiagsEntry
    MAX-ACCESS  not-accessible
    STATUS      current
    DESCRIPTION
        "This table contains RPD Ethernet diagnostics."
    ::= { cerRphyMib 72 }

cerRpdEnetDiagsEntry OBJECT-TYPE
    SYNTAX      CerRpdEnetDiagsEntry
    MAX-ACCESS  not-accessible
    STATUS      current
    DESCRIPTION
        "An entry for the RpdEnetDiags table."
    INDEX { cerRpdEnetDiagsRpdIndex, cerRpdEnetDiagsEthPortIndex }
    ::= { cerRpdEnetDiagsTable 1 }

CerRpdEnetDiagsEntry ::= SEQUENCE {
    cerRpdEnetDiagsRpdIndex          CerRpdIndex,
    cerRpdEnetDiagsEthPortIndex      Unsigned32,
    cerRpdEnetDiagsTxPower           Unsigned32,
    cerRpdEnetDiagsRxPower           Unsigned32,
    cerRpdEnetDiagsTxBias            Unsigned32,
    cerRpdEnetDiagsTemp              Integer32,
    cerRpdEnetDiagsVcc               Unsigned32
}

cerRpdEnetDiagsRpdIndex OBJECT-TYPE
    SYNTAX      CerRpdIndex
    MAX-ACCESS  not-accessible
    STATUS      current
    DESCRIPTION
        "The index of the RPD."
    ::= { cerRpdEnetDiagsEntry 1 }

cerRpdEnetDiagsEthPortIndex OBJECT-TYPE
    SYNTAX      Unsigned32
    MAX-ACCESS  not-accessible
    STATUS      current
    DESCRIPTION
        "RPD Ethernet port index."
    ::= { cerRpdEnetDiagsEntry 2 }

cerRpdEnetDiagsTxPower OBJECT-TYPE
    SYNTAX      Unsigned32
    UNITS       "decibel-milliwatts (dBm)"
    MAX-ACCESS  read-only
    STATUS      current
    DESCRIPTION
        "Ethernet transmit output power. Read using ARRIS TLV 21.7.2."
    ::= { cerRpdEnetDiagsEntry 3 }

cerRpdEnetDiagsRxPower OBJECT-TYPE
    SYNTAX      Unsigned32
    UNITS       "decibel-milliwatts (dBm)"
    MAX-ACCESS  read-only
    STATUS      current
    DESCRIPTION
        "Ethernet receive input power. Read using ARRIS TLV 21.7.3."
    ::= { cerRpdEnetDiagsEntry 4 }

cerRpdEnetDiagsTxBias OBJECT-TYPE
    SYNTAX      Unsigned32
    UNITS       "milliamps (mA)"
    MAX-ACCESS  read-only
    STATUS      current
    DESCRIPTION
        "Ethernet transmit bias current. Read using ARRIS TLV 21.7.4."
    ::= { cerRpdEnetDiagsEntry 5 }

cerRpdEnetDiagsTemp OBJECT-TYPE
    SYNTAX      Integer32
    UNITS       "degrees Celsius"
    MAX-ACCESS  read-only
    STATUS      current
    DESCRIPTION
        "Ethernet temperature. Read using ARRIS TLV 21.7.5."
    ::= { cerRpdEnetDiagsEntry 6 }

cerRpdEnetDiagsVcc OBJECT-TYPE
    SYNTAX      Unsigned32
    UNITS       "Volts"
    MAX-ACCESS  read-only
    STATUS      current
    DESCRIPTION
        "Ethernet supply voltage. Read using ARRIS TLV 21.7.6."
    ::= { cerRpdEnetDiagsEntry 7 }

--------------------------------------------------------------------------------------------------
-- RPHY US Preamble tables
--------------------------------------------------------------------------------------------------

cerRphyUsScQamConfigPreambleTable OBJECT-TYPE
        SYNTAX      SEQUENCE OF CerRphyUsScQamConfigPreambleEntry
        MAX-ACCESS  not-accessible
        STATUS      current
        DESCRIPTION
            "This table stores configured preamble superstrings for 
             SC-QAM UCDs sent to an RPD."
        ::= { cerRphyMib 73 }

cerRphyUsScQamConfigPreambleEntry OBJECT-TYPE
        SYNTAX      CerRphyUsScQamConfigPreambleEntry
        MAX-ACCESS  not-accessible
        STATUS      current
        DESCRIPTION
            "An entry defines one SC-QAM configured preamble superstring,
             its description and index."
        INDEX { cerRphyUsScQamConfigPreambleIndex }
        ::= { cerRphyUsScQamConfigPreambleTable 1 }

CerRphyUsScQamConfigPreambleEntry ::= SEQUENCE {
            cerRphyUsScQamConfigPreambleIndex        Unsigned32 ,
            cerRphyUsScQamConfigPreambleSuperstring  OCTET STRING,
            cerRphyUsScQamConfigPreambleDescription  SnmpAdminString,
            cerRphyUsScQamConfigPreambleRowStatus    RowStatus
        }

cerRphyUsScQamConfigPreambleIndex OBJECT-TYPE
        SYNTAX     Unsigned32 (1..256)
        MAX-ACCESS not-accessible
        STATUS     current
        DESCRIPTION
            "The configured index of this preamble superstring"
        ::= { cerRphyUsScQamConfigPreambleEntry 1 }

cerRphyUsScQamConfigPreambleSuperstring OBJECT-TYPE
        SYNTAX      OCTET STRING (SIZE(1..192)) 
        MAX-ACCESS read-create
        STATUS      current
        DESCRIPTION
            "The preamble superstring that goes in the UCD"
        ::= { cerRphyUsScQamConfigPreambleEntry 2 }

cerRphyUsScQamConfigPreambleDescription  OBJECT-TYPE
        SYNTAX      SnmpAdminString (SIZE (0..32))
        MAX-ACCESS  read-create
        STATUS      current
        DESCRIPTION
            "Description of this SC-QAM preamble superstring, 
             such as what kind of RPD it goes with."
        DEFVAL { "" }
        ::= { cerRphyUsScQamConfigPreambleEntry 3 }

cerRphyUsScQamConfigPreambleRowStatus     OBJECT-TYPE
        SYNTAX      RowStatus
        MAX-ACCESS  read-create
        STATUS      current
        DESCRIPTION
            "The RowStatus for controlling entries in this table."
        ::= { cerRphyUsScQamConfigPreambleEntry 4 }


cerRphyUsScQamModPreambleTable OBJECT-TYPE
        SYNTAX      SEQUENCE OF CerRphyUsScQamModPreambleEntry 
        MAX-ACCESS  not-accessible
        STATUS      current
        DESCRIPTION
            "This table associates an SC-QAM US modulation profile with a 
             configured preamble superstring for UCDs sent to an RPD."
        ::= { cerRphyMib 74 }

cerRphyUsScQamModPreambleEntry OBJECT-TYPE
        SYNTAX      CerRphyUsScQamModPreambleEntry 
        MAX-ACCESS  not-accessible
        STATUS      current
        DESCRIPTION
            "An entry associates an SC-QAM US modulation profile index 
             with a configured preamble index"
        INDEX { cadIfCmtsModIndex }
        ::= { cerRphyUsScQamModPreambleTable 1 }

CerRphyUsScQamModPreambleEntry ::= SEQUENCE {
            cerRphyUsScQamModPreambleStringIndex Unsigned32,
            cerRphyUsScQamModPreambleRowStatus   RowStatus
        }

cerRphyUsScQamModPreambleStringIndex OBJECT-TYPE
        SYNTAX     Unsigned32 (1..256)
        MAX-ACCESS read-create
        STATUS      current
        DESCRIPTION
            "The index of the configured SC-QAM preamble superstring
             from cerRphyUsScQamConfigPreambleTable that goes in the UCD
             for SC-QAM US's associated with the SC-QAM US modulation profile."
        ::= { cerRphyUsScQamModPreambleEntry 1 }

cerRphyUsScQamModPreambleRowStatus OBJECT-TYPE
        SYNTAX      RowStatus
        MAX-ACCESS  read-create
        STATUS      current
        DESCRIPTION
            "The RowStatus for controlling entries in this table."
        ::= {cerRphyUsScQamModPreambleEntry 2 }


cerRphyUsOfdmaTmpltPreambleTable OBJECT-TYPE
        SYNTAX      SEQUENCE OF CerRphyUsOfdmaTmpltPreambleEntry 
        MAX-ACCESS  not-accessible
        STATUS      current
        DESCRIPTION
            "This table associates an OFDMA US modulation profile with a configured
             preamble superstring for UCDs sent to an RPD."
        ::= { cerRphyMib 75 }

cerRphyUsOfdmaTmpltPreambleEntry OBJECT-TYPE
        SYNTAX      CerRphyUsOfdmaTmpltPreambleEntry 
        MAX-ACCESS  not-accessible
        STATUS      current
        DESCRIPTION
            "An entry associates an OFDMA US modulation profile index with
             a configured preamble index"
        INDEX { cadIfUsOfdmaTmpltIndex }
        ::= { cerRphyUsOfdmaTmpltPreambleTable 1 }

CerRphyUsOfdmaTmpltPreambleEntry ::= SEQUENCE {
            cerRphyUsOfdmaTmpltPreambleStringIndex   Unsigned32,
            cerRphyUsOfdmaTmpltRandomizationSeed     Unsigned32,
            cerRphyUsOfdmaTmpltInitRngPreambleOffset Unsigned32,
            cerRphyUsOfdmaTmpltFineRngPreambleOffset Unsigned32,
            cerRphyUsOfdmaTmpltPreambleRowStatus     RowStatus
        }

cerRphyUsOfdmaTmpltPreambleStringIndex OBJECT-TYPE
        SYNTAX     Unsigned32 (1..256)
        MAX-ACCESS read-create
        STATUS      current
        DESCRIPTION
            "The index of the configured OFDMA preamble superstring stored in
             ceRphyUsOfdmaConfigPreambleTable that goes in the UCD 
             for OFDMA US's associated with the OFDMA US modulation profile."
        ::= { cerRphyUsOfdmaTmpltPreambleEntry 1 }

cerRphyUsOfdmaTmpltRandomizationSeed OBJECT-TYPE
         SYNTAX Unsigned32 (0..8388607)
         MAX-ACCESS read-create
         STATUS current
         DESCRIPTION
             "23-bit randomization seed for the OFDMA channel. The value is right-justified
              in the 3-byte field. This value goes in TLV 33 in the OFDMA UCD."
         DEFVAL { 0 }
         ::= { cerRphyUsOfdmaTmpltPreambleEntry 2 }

cerRphyUsOfdmaTmpltInitRngPreambleOffset OBJECT-TYPE
         SYNTAX Unsigned32 (0..1535)
         MAX-ACCESS read-create
         STATUS current
         DESCRIPTION
             "IUC 3 offset into the configured preamble superstring; if the offset says 100, IUC 3 
              preamble starts at bit 101 of the superstring. This value goes in the UCD in TLV 23.4 
              for the IUC 3 burst descriptor. 
              Note that the preamble length for IUC 3 that goes in the UCD in TLV 23.3 is calculated from
              (cadIfUsOfdmaTmpltInitRngFreqWidth * cadIfUsOfdmaTmpltInitRngPreambleLen)."
         DEFVAL { 0 }
         ::= { cerRphyUsOfdmaTmpltPreambleEntry 3 }

cerRphyUsOfdmaTmpltFineRngPreambleOffset OBJECT-TYPE
         SYNTAX Unsigned32 (0..1535)
         MAX-ACCESS read-create
         STATUS current
         DESCRIPTION
             "IUC 4 offset into the configured preamble superstring; if the offset says 100, IUC 4 
              preamble starts at bit 101 of the superstring. This value goes in the UCD in TLV 23.4 
              for the IUC 4 burst descriptor. 
              Note that the preamble length for IUC 4 that goes in the UCD in TLV 23.3 is 
              equal to cadIfUsOfdmaTmpltFineRngFreqWidth."
         DEFVAL { 0 }
         ::= { cerRphyUsOfdmaTmpltPreambleEntry 4 }

cerRphyUsOfdmaTmpltPreambleRowStatus  OBJECT-TYPE
        SYNTAX      RowStatus
        MAX-ACCESS  read-create
        STATUS      current
        DESCRIPTION
            "The RowStatus for controlling entries in this table."
        ::= { cerRphyUsOfdmaTmpltPreambleEntry 5 }


cerRphyUsOfdmaConfigPreambleTable OBJECT-TYPE
        SYNTAX      SEQUENCE OF CerRphyUsOfdmaConfigPreambleEntry
        MAX-ACCESS  not-accessible
        STATUS      current
        DESCRIPTION
            "This table stores configured preamble superstrings for OFDMA UCDs sent to an RPD."
        ::= { cerRphyMib 76 }

cerRphyUsOfdmaConfigPreambleEntry OBJECT-TYPE
        SYNTAX      CerRphyUsOfdmaConfigPreambleEntry
        MAX-ACCESS  not-accessible
        STATUS      current
        DESCRIPTION
            "An entry defines one OFDMA configured preamble superstring, its description and index."
        INDEX { cerRphyUsOfdmaConfigPreambleIndex }
        ::= { cerRphyUsOfdmaConfigPreambleTable 1 }

CerRphyUsOfdmaConfigPreambleEntry ::= SEQUENCE {
            cerRphyUsOfdmaConfigPreambleIndex        Unsigned32 ,
            cerRphyUsOfdmaConfigPreambleSuperstring  OCTET STRING,
            cerRphyUsOfdmaConfigPreambleDescription  SnmpAdminString,
            cerRphyUsOfdmaConfigPreambleRowStatus    RowStatus
        }

cerRphyUsOfdmaConfigPreambleIndex OBJECT-TYPE
        SYNTAX     Unsigned32 (1..256)
        MAX-ACCESS not-accessible
        STATUS     current
        DESCRIPTION
            "The configured index of this preamble superstring"
    ::= { cerRphyUsOfdmaConfigPreambleEntry 1 }

cerRphyUsOfdmaConfigPreambleSuperstring OBJECT-TYPE
        SYNTAX      OCTET STRING (SIZE(1..192)) 
        MAX-ACCESS read-create
        STATUS      current
        DESCRIPTION
            "The preamble superstring that goes in the OFDMA UCD"
        ::= { cerRphyUsOfdmaConfigPreambleEntry 2 }

cerRphyUsOfdmaConfigPreambleDescription  OBJECT-TYPE
        SYNTAX      SnmpAdminString (SIZE (0..32))
        MAX-ACCESS  read-create
        STATUS      current
        DESCRIPTION
            "Description of this OFDMA preamble superstring, such as what kind of RPD it goes with."
        DEFVAL { "" }
        ::= { cerRphyUsOfdmaConfigPreambleEntry 3 }

cerRphyUsOfdmaConfigPreambleRowStatus     OBJECT-TYPE
        SYNTAX      RowStatus
        MAX-ACCESS  read-create
        STATUS      current
        DESCRIPTION
            "The RowStatus for controlling entries in this table."
        ::= { cerRphyUsOfdmaConfigPreambleEntry 4 }

--------------------------------------------------------------------------------------------------
-- RPD ScQam and Ofdma Query tables
--------------------------------------------------------------------------------------------------

cerRpdUsScQamQueryControlGroup OBJECT IDENTIFIER ::= {cerRphyMib 77}

    cerRpdUsScQamQueryControlRpdIndex OBJECT-TYPE
        SYNTAX CerRpdIndex
        MAX-ACCESS read-write
        STATUS current
        DESCRIPTION
            "Global index for this RPD."
        ::= { cerRpdUsScQamQueryControlGroup 1 }

    cerRpdUsScQamQueryControlModIndex OBJECT-TYPE
        SYNTAX Integer32 (1..2147483647)
        MAX-ACCESS read-write
        STATUS current
        DESCRIPTION
            "Index of the SC-QAM modulation profile whose parameters are sent to the RPD in TLV 150 UsScQamProfileQuery."
        ::= { cerRpdUsScQamQueryControlGroup 2 }

    cerRpdUsScQamQueryControlEnable OBJECT-TYPE
        SYNTAX TruthValue
        MAX-ACCESS read-write
        STATUS current
        DESCRIPTION 
            "Setting this attribute to true causes the CMTS to begin the process of sending TLV 150 
             UsScQamProfileQuery and 151 UsScQamProfileResponse to the RPD."
        ::= { cerRpdUsScQamQueryControlGroup 3 }

cerRpdUsScQamIucResponseTable OBJECT-TYPE
         SYNTAX SEQUENCE OF CerRpdUsScQamIucResponseEntry 
         MAX-ACCESS not-accessible
         STATUS current
         DESCRIPTION
             "This table stores what an RPD sent in TLV 151.2 which are recommended parameters per IUC.
              The superstring returned in TLV 151.1 is stored in cerRpdUsScQamPreambleResponseSuperstring.
              The RPD that sent TLV 151 is stored in cerRpdUsScQamSuperstringResponseRpdIndex. The SC-QAM 
              modulation profile used to populate TLV 150 is stored in cerRpdUsScQamSuperstringResponseModIndex.
              Only one response is stored in this table at a time; new responses overwrite existing responses."
        ::= { cerRphyMib 78 }

cerRpdUsScQamIucResponseEntry OBJECT-TYPE
        SYNTAX CerRpdUsScQamIucResponseEntry 
        MAX-ACCESS not-accessible
        STATUS current
        DESCRIPTION
            "This table stores what an RPD sent in TLV 151.2 which are recommended parameters per IUC.
             The values returned in TLV 151 that are not per IUC are stored in MIB variables that are 
             part of cerRpdUsScQamSuperstringResponseGroup. The RPD and SC-QAM modulation profile related
             to TLV 151 are also stored in MIB variables in cerRpdUsScQamSuperstringResponseGroup. 
             Only one response is stored in this table at a time; new responses overwrite existing responses."
        INDEX { cerRpdUsScQamIucResponseIucIndex}
        ::= { cerRpdUsScQamIucResponseTable 1 }

CerRpdUsScQamIucResponseEntry ::= SEQUENCE {
         cerRpdUsScQamIucResponseIucIndex INTEGER,
         cerRpdUsScQamIucResponseLength Integer32,
         cerRpdUsScQamIucResponseOffset Integer32,
         cerRpdUsScQamIucResponseModType INTEGER,
         cerRpdUsScQamIucResponseScramblerSeed Integer32,
         cerRpdUsScQamIucResponseGuardTime Unsigned32,
         cerRpdUsScQamIucResponseRpdIndex CerRpdIndex
    }

cerRpdUsScQamIucResponseIucIndex OBJECT-TYPE
         SYNTAX INTEGER {
                 request(1),
                 requestData(2),
                 initialRanging(3),
                 periodicRanging(4),
                 shortData(5),
                 longData(6),
                 advPhyShortData(9),
                 advPhyLongData(10),
                 ugs(11)
         }
         MAX-ACCESS not-accessible
         STATUS current
         DESCRIPTION
             "US SC-QAM IUC related to this subset of RPD recommended preamble settings, from TLV 151.2.1 ResponseScQamCode."
         ::= { cerRpdUsScQamIucResponseEntry 1 }

cerRpdUsScQamIucResponseLength OBJECT-TYPE
         SYNTAX Integer32 (0..1536)
         MAX-ACCESS read-only
         STATUS current
         DESCRIPTION
                 "The RPD's recommended preamble length for this IUC in bits, from TLV 151.2.2 ResponseScQamPreambleLen."
         DEFVAL { 0 }
         ::= { cerRpdUsScQamIucResponseEntry 2 }

cerRpdUsScQamIucResponseOffset OBJECT-TYPE
        SYNTAX Integer32
        MAX-ACCESS read-only
        STATUS current
        DESCRIPTION
            "The RPD's recommended offset into the preamble superstring for this IUC, from TLV 151.2.3 
             ResponseScQamPreambleOffset."
         DEFVAL { 0 }
         ::= { cerRpdUsScQamIucResponseEntry 3 }

cerRpdUsScQamIucResponseModType OBJECT-TYPE
        SYNTAX INTEGER {
                 qpsk0(1),
                 qpsk1(2)
         }
         MAX-ACCESS read-only
         STATUS current
         DESCRIPTION
             "The RPD's recommended preamble type, from TLV 151.2.4 ResponseScQamPreambleModType."
         DEFVAL { qpsk0 }
         ::= { cerRpdUsScQamIucResponseEntry 4 }

cerRpdUsScQamIucResponseScramblerSeed OBJECT-TYPE
         SYNTAX Integer32 (0..32767)
         MAX-ACCESS read-only
         STATUS current
         DESCRIPTION
             "The RPD's recommended value for the upstream scrambler seed in the RPD, from TLV 151.2.5 
              ResponseScQamScramblerSeed. The leftmost 15 bytes in the 2 byte field are used."
         DEFVAL { 0 }
         ::= { cerRpdUsScQamIucResponseEntry 5 }

cerRpdUsScQamIucResponseGuardTime OBJECT-TYPE
        SYNTAX Unsigned32 (8..96)
        MAX-ACCESS read-only
        STATUS current
        DESCRIPTION
             "The RPD's recommended value for the number of symbol-times which must follow the end of
              this channel's burst, from TLV 151.2.6 ResponseScQamGuardTime. A value of 0 is only valid
              for SCDMA modulation profiles, which are not supported."
        DEFVAL { 8 }
        ::= { cerRpdUsScQamIucResponseEntry 6 }

cerRpdUsScQamIucResponseRpdIndex OBJECT-TYPE
         SYNTAX CerRpdIndex
         MAX-ACCESS read-only
         STATUS current
         DESCRIPTION
              "Global index for the RPD that sent the most recent SC-QAM US preamble response in TLV 151."
         ::= { cerRpdUsScQamIucResponseEntry 7 }

cerRpdUsScQamSuperstringResponseGroup OBJECT IDENTIFIER ::= { cerRphyMib 79 }

    cerRpdUsScQamSuperstringResponseRpdIndex OBJECT-TYPE
         SYNTAX CerRpdIndex
         MAX-ACCESS read-only
         STATUS current
         DESCRIPTION
                  "Global index for the RPD that sent the most recent SC-QAM US preamble response in TLV 151."
         ::= { cerRpdUsScQamSuperstringResponseGroup 1 }

    cerRpdUsScQamPreambleResponseSuperstring OBJECT-TYPE
         SYNTAX      OCTET STRING (SIZE(0..192)) 
         MAX-ACCESS read-only
         STATUS      current
         DESCRIPTION
            "The RPD's recommended preamble superstring for the SC-QAM UCD, sent to the Core in TLV 151.1 
             ResponseScQamPreambleString. This also applies to the data per IUC from TLV 151 stored in 
             cerRpdUsScQamIucResponseTable."
         DEFVAL { ''h }
         ::= { cerRpdUsScQamSuperstringResponseGroup 2 }

    cerRpdUsScQamPreambleResponseTimestamp OBJECT-TYPE
        SYNTAX DateAndTime
        MAX-ACCESS read-only
        STATUS current
        DESCRIPTION
            "The date and time that TLV 151 UsScQamProfileResponse was received from this RPD. 
             This also applies to the data per IUC from TLV 151 stored in cerRpdUsScQamIucResponseTable."
        DEFVAL { '0000000000000000'h }
        ::= { cerRpdUsScQamSuperstringResponseGroup 3 }


cerRpdUsOfdmaQueryControlGroup OBJECT IDENTIFIER ::= {cerRphyMib 80} 

   cerRpdUsOfdmaQueryControlRpdIndex OBJECT-TYPE
        SYNTAX CerRpdIndex
        MAX-ACCESS read-write
        STATUS current
        DESCRIPTION
             "Global index for this RPD."
        ::= { cerRpdUsOfdmaQueryControlGroup 1 }

   cerRpdUsOfdmaQueryControlTmpltIndex OBJECT-TYPE
        SYNTAX CadOfdmaDataTemplateIndexType
        MAX-ACCESS read-write
        STATUS current
        DESCRIPTION
            "Index of the OFDMA modulation profile whose parameters are sent to the RPD
             in TLV 152 UsOfdmaConfigQuery."
        ::= { cerRpdUsOfdmaQueryControlGroup 2 }

   cerRpdUsOfdmaQueryControlEnable OBJECT-TYPE
        SYNTAX TruthValue
        MAX-ACCESS read-write
        STATUS current
        DESCRIPTION 
            "Setting this attribute to true causes the CMTS to begin the process of sending
             TLV 152 UsOfdmaConfigQuery and 153 UsOfdmaConfigResponse to the RPD."
        ::= { cerRpdUsOfdmaQueryControlGroup 3 }


cerRpdUsOfdmaPreambleResponseGroup OBJECT IDENTIFIER ::= {cerRphyMib 81 }

   cerRpdUsOfdmaPreambleResponseRpdIndex OBJECT-TYPE
       SYNTAX CerRpdIndex
       MAX-ACCESS read-only
       STATUS current
       DESCRIPTION
           "Global index for the RPD that sent TLV 153."
       ::= { cerRpdUsOfdmaPreambleResponseGroup 1 }

   cerRpdUsOfdmaPreambleResponseTmpltIndex OBJECT-TYPE
       SYNTAX CadOfdmaDataTemplateIndexType
       MAX-ACCESS read-only
       STATUS current
       DESCRIPTION
           "Index of the OFDMA modulation profile whose parameters were sent to the RPD in
            TLV 152 and for which the RPD crafted the superstring in TLV 153.3."
       DEFVAL { 1 }
       ::= { cerRpdUsOfdmaPreambleResponseGroup 2 }

   cerRpdUsOfdmaPreambleResponseRolloffPeriod OBJECT-TYPE
       SYNTAX Integer32 (0|32|64|96|128|160|192|224)
       UNITS "samples"
       MAX-ACCESS read-only
       STATUS current
       DESCRIPTION
           "The RPD's recommended roll-off period used in windowing, sent in TLV 153. 1, 
            converted into samples using the sample rate of 102.4 Million samples/second."
       DEFVAL { 0 }
       ::= { cerRpdUsOfdmaPreambleResponseGroup 3 }

   cerRpdUsOfdmaPreambleResponseCyclicPrefix OBJECT-TYPE
       SYNTAX Integer32 (96|128|160|192|224|256|288|320|384|512|640)
       UNITS "samples"
       MAX-ACCESS read-only
       STATUS current
       DESCRIPTION
           "The RPD's recommended cyclic-prefix, sent in TLV 153.2, 
            converted into samples using the sample rate of 102.4 Million samples/second."
       DEFVAL { 96 }
       ::= { cerRpdUsOfdmaPreambleResponseGroup 4 }

   cerRpdUsOfdmaPreambleResponseSymbolsPerFrame OBJECT-TYPE
        SYNTAX      Integer32 (6..36)
        UNITS       "symbols"
        MAX-ACCESS  read-only
        STATUS      current
        DESCRIPTION
            "The RPD's recommended value for K, the number of symbols per frame (minislot), sent in TLV 153.4."
        DEFVAL { 16 }
        ::= { cerRpdUsOfdmaPreambleResponseGroup 5 }

   cerRpdUsOfdmaPreambleResponseRandomizationSeed OBJECT-TYPE
        SYNTAX      Integer32 (0..8388607)
        MAX-ACCESS  read-only
        STATUS      current
        DESCRIPTION
            "The RPD's recommended value from TLV 153.5 for the OFDMA randomization seed in UCD TLV 33. 
            The rightmost 23 bits are used."
        DEFVAL { 0 }
        ::= { cerRpdUsOfdmaPreambleResponseGroup 6 }

   cerRpdUsOfdmaResponsePreambleInitRngOffset OBJECT-TYPE
         SYNTAX Unsigned32 (0..1535)
         MAX-ACCESS read-only
         STATUS current
         DESCRIPTION
              "RPD's recommended value for IUC 3 offset into the preamble superstring."
         DEFVAL { 0 }
         ::= { cerRpdUsOfdmaPreambleResponseGroup 7 }

   cerRpdUsOfdmaResponsePreambleFineRngOffset OBJECT-TYPE
         SYNTAX Unsigned32 (0..1535)
         MAX-ACCESS read-only
         STATUS current
         DESCRIPTION
                 "RPD's recommended value for IUC 4 offset into the preamble superstring."
         DEFVAL { 0 }
         ::= { cerRpdUsOfdmaPreambleResponseGroup 8 }

   cerRpdUsOfdmaPreambleResponseSuperstring OBJECT-TYPE
        SYNTAX      OCTET STRING (SIZE(0..192)) 
        MAX-ACCESS read-only
        STATUS      current
        DESCRIPTION
            "The RPD's recommended preamble superstring for the OFDMA UCD, 
             sent in TLV 153.3 ResponseOfdmaPreambleString"
        DEFVAL { ''h }
        ::= { cerRpdUsOfdmaPreambleResponseGroup 9 }

   cerRpdUsOfdmaPreambleResponseTimestamp OBJECT-TYPE
        SYNTAX DateAndTime
        MAX-ACCESS read-only
        STATUS current
        DESCRIPTION
            "The date and time that TLV 153 UsOfdmaConfigResponse was received from this RPD."
        DEFVAL { '0000000000000000'h }
        ::= { cerRpdUsOfdmaPreambleResponseGroup 10 }

--
--  RPD Upstream RF ports
--
cerRpdUsRfPortTable OBJECT-TYPE
        SYNTAX SEQUENCE OF CerRpdUsRfPortEntry
        MAX-ACCESS not-accessible
        STATUS current
        DESCRIPTION
            "This table contains the US RPD RF
             ports."
        ::= { cerRphyMib 82 }
        
cerRpdUsRfPortEntry OBJECT-TYPE
        SYNTAX CerRpdUsRfPortEntry
        MAX-ACCESS not-accessible
        STATUS current
        DESCRIPTION
            "An entry for the table."
        INDEX { cerRpdUsRfPortRpdIndex, cerRpdUsRfPortRpdRfPortId}
        ::= { cerRpdUsRfPortTable 1 }
        
CerRpdUsRfPortEntry ::= SEQUENCE {
           cerRpdUsRfPortRpdIndex 		CerRpdIndex,
           cerRpdUsRfPortRpdRfPortId 	Unsigned32,
           cerRpdUsRfPortBasePowerLevel Integer32,
           cerRpdUsRfPortRowstatus 		RowStatus,
           cerRpdUsRfPortSfLevel		INTEGER
        }
cerRpdUsRfPortRpdIndex OBJECT-TYPE
        SYNTAX CerRpdIndex
        MAX-ACCESS not-accessible
        STATUS current
        DESCRIPTION
            "Global index for this RPD."
        ::= { cerRpdUsRfPortEntry 1 }
        
cerRpdUsRfPortRpdRfPortId  OBJECT-TYPE
        SYNTAX Unsigned32 (1..4)
        MAX-ACCESS not-accessible
        STATUS current
        DESCRIPTION
            "Index of DS RF port on the RPD."
        ::= { cerRpdUsRfPortEntry 2}
        
cerRpdUsRfPortBasePowerLevel  OBJECT-TYPE
        SYNTAX Integer32
        UNITS "TenthDbMv"
        MAX-ACCESS read-create
        STATUS current
        DESCRIPTION
            "The base power level for this US RPD RF port normalized to
             1.6 MHz channel width."
        DEFVAL { 20 }
        ::= { cerRpdUsRfPortEntry 3 }
        
cerRpdUsRfPortRowstatus  OBJECT-TYPE
        SYNTAX RowStatus
        MAX-ACCESS read-create
        STATUS current
        DESCRIPTION
            "The RowStatus for controlling entries in this table.
             Allowed values are createAndGo, destroy, and active."
        ::= { cerRpdUsRfPortEntry 4 }

cerRpdUsRfPortSfLevel OBJECT-TYPE
        SYNTAX INTEGER {
            medium(1),
            high(2)
        }
        MAX-ACCESS read-create
        STATUS current
        DESCRIPTION
            "The level of total SFs (bonded plus non-bonded) allowed on this RPD US RF port."
        DEFVAL { medium }
        ::= { cerRpdUsRfPortEntry 5}
--
-- power adjustment for RPD Upstream SC-QAM/OFDMA channels
--

cerRphyTargetPowerAdjTable OBJECT-TYPE
    SYNTAX SEQUENCE OF CerRphyTargetPowerAdjEntry
    MAX-ACCESS not-accessible
    STATUS current
    DESCRIPTION
        "This table contains the incremental US target power level adjustment US RPHY channels."
    ::= { cerRphyMib 83 }

cerRphyTargetPowerAdjEntry OBJECT-TYPE
    SYNTAX CerRphyTargetPowerAdjEntry
    MAX-ACCESS not-accessible
    STATUS current
    DESCRIPTION
        "An entry for the table."
    INDEX { cerRphyTargetPowerAdjChanIfIndex}
    ::= { cerRphyTargetPowerAdjTable 1}

CerRphyTargetPowerAdjEntry ::= SEQUENCE {
    cerRphyTargetPowerAdjChanIfIndex                InterfaceIndex,
    cerRphyTargetPowerAdjPowerLevel                 Integer32,
    cerRphyTargetPowerAdjRowStatus                  RowStatus
}

cerRphyTargetPowerAdjChanIfIndex OBJECT-TYPE
    SYNTAX InterfaceIndex
    MAX-ACCESS not-accessible
    STATUS current
    DESCRIPTION
        "Core IfIndex for this US channel."
    ::= { cerRphyTargetPowerAdjEntry 1}

cerRphyTargetPowerAdjPowerLevel OBJECT-TYPE
    SYNTAX      Integer32
    UNITS       "TenthdB"
    MAX-ACCESS  read-create
    STATUS      current
    DESCRIPTION
        "The incremental target power level adjustment for this US channel. Total channel power normalized to
          1.6 MHz is this value plus cerRpdUsBasePowerLevel for the channels RF port."
    DEFVAL { 0 }
    ::= { cerRphyTargetPowerAdjEntry 2 }

cerRphyTargetPowerAdjRowStatus OBJECT-TYPE
    SYNTAX      RowStatus
    MAX-ACCESS  read-create
    STATUS      current
    DESCRIPTION
        "The RowStatus for controlling entries in this table. 
         Allowed values are createAndGo, destroy, and active."
    ::= { cerRphyTargetPowerAdjEntry 3 }

-- ---------------------------------------------------------------------
-- The CMTS Upstream Triggered Spectrum Capture Config Table
-- ---------------------------------------------------------------------
cerPnmCmtsUtscCfgTable OBJECT-TYPE
     SYNTAX      SEQUENCE OF CerPnmCmtsUtscCfgEntry
     MAX-ACCESS  not-accessible
     STATUS      current
     DESCRIPTION
        "This table provides configuration functionality for the Core
         Upstream Triggered Spectrum Capture function."
     ::= { cerRphyMib 84 }

cerPnmCmtsUtscCfgEntry OBJECT-TYPE
     SYNTAX      CerPnmCmtsUtscCfgEntry
     MAX-ACCESS  not-accessible
     STATUS      current
     DESCRIPTION
         "The conceptual row of the cerPnmCmtsUtscCfgTable.
          The conceptual rows does not persist across device resets.
          A separate entry exists for every Upstream RF Port
          which supports the capability.
          This table supports the creation and deletion of at least one
          instance."
     INDEX { ifIndex,
             cerPnmCmtsUtscCfgIndex }
     ::= { cerPnmCmtsUtscCfgTable 1 }

CerPnmCmtsUtscCfgEntry ::= SEQUENCE {
    cerPnmCmtsUtscCfgIndex                  Unsigned32,
    cerPnmCmtsUtscCfgStaticPwDestIpAddrType InetAddressType,
    cerPnmCmtsUtscCfgStaticPwDestIpAddr     InetAddressIPv4or6,
    cerPnmCmtsUtscCfgStaticPwSessionId      Unsigned32,
    cerPnmCmtsUtscCfgStaticPwSrcIpAddr      InetAddressIPv4or6,
    cerPnmCmtsUtscCfgStaticPwSrcEnetPort    Unsigned32
}

cerPnmCmtsUtscCfgIndex OBJECT-TYPE
     SYNTAX      Unsigned32 (0..4294967295)
     MAX-ACCESS  not-accessible
     STATUS      current
     DESCRIPTION
        "This key attribute is a unique identifier for a particular set
         of configuration settings. If the CORE does not support
         multiple Upstream Triggered Spectrum Sample Capture
         configuration settings, the CORE MUST only support a value of 1
         for this attribute and reject any attempt to configure it to a
         value other than 1."
     ::= { cerPnmCmtsUtscCfgEntry 1 }

cerPnmCmtsUtscCfgStaticPwDestIpAddrType OBJECT-TYPE
     SYNTAX      InetAddressType
     MAX-ACCESS  read-write
     STATUS      current
     DESCRIPTION
        "This attribute is the address type of the static psuedowires
         used between the RPD and the PNM server."
     DEFVAL { ipv6 }
     ::= { cerPnmCmtsUtscCfgEntry 2 }

cerPnmCmtsUtscCfgStaticPwDestIpAddr OBJECT-TYPE
     SYNTAX      InetAddressIPv4or6
     MAX-ACCESS  read-write
     STATUS      current
     DESCRIPTION
        "This attribute is the IP address of the PNM server that is
         the destination for all PNM UEPI packets from the RPD."
     DEFVAL { '00000000000000000000000000000000'H }
     ::= { cerPnmCmtsUtscCfgEntry 3 }

cerPnmCmtsUtscCfgStaticPwSessionId OBJECT-TYPE
     SYNTAX      Unsigned32
     MAX-ACCESS  read-only
     STATUS      current
     DESCRIPTION
        "This attribute shows the sessionId of the static psuedowire
         used for the PNM UEPI packets from the RPD."
     DEFVAL { 0 }
     ::= { cerPnmCmtsUtscCfgEntry 4 }

cerPnmCmtsUtscCfgStaticPwSrcIpAddr OBJECT-TYPE
     SYNTAX      InetAddressIPv4or6
     MAX-ACCESS  read-only
     STATUS      current
     DESCRIPTION
        "This attribute shows the source IP address used for the
         UEPI PNM packets from the RPD."
     DEFVAL { '00000000000000000000000000000000'H }
     ::= { cerPnmCmtsUtscCfgEntry 5 }

cerPnmCmtsUtscCfgStaticPwSrcEnetPort OBJECT-TYPE
     SYNTAX      Unsigned32 (0..1)
     MAX-ACCESS  read-only
     STATUS      current
     DESCRIPTION
        "This attribute shows the ethernet port associated 
         with the source IP address used for the
         UEPI PNM packets from the RPD."
     DEFVAL { 0 }
     ::= { cerPnmCmtsUtscCfgEntry 6 }

-- ---------------------------------------------------------------------
-- The RPD Aux Core Config Table
-- ---------------------------------------------------------------------     
cerRpdAuxCoreTable OBJECT-TYPE
    SYNTAX SEQUENCE OF CerRpdAuxCoreEntry
    MAX-ACCESS not-accessible
    STATUS current
    DESCRIPTION
        "This table contains the IP addresses of AUX cores to be sent in TLV 88 to a specific RPD.
          A row in this table for an RPD supersedes use of the global AUX cores in the cerRphyAuxCoreTable
         for that RPD."
    ::= { cerRphyMib 86 }

cerRpdAuxCoreEntry OBJECT-TYPE
    SYNTAX CerRpdAuxCoreEntry
    MAX-ACCESS not-accessible
    STATUS current
    DESCRIPTION
        "An entry for the table."
    INDEX { cerRpdAuxCoreRpdIndex, cerRpdAuxCoreAddrType, cerRpdAuxCoreIpAddr }
    ::= {cerRpdAuxCoreTable 1}

CerRpdAuxCoreEntry ::= SEQUENCE {
    cerRpdAuxCoreRpdIndex           CerRpdIndex,
    cerRpdAuxCoreAddrType           InetAddressType,
    cerRpdAuxCoreIpAddr             InetAddressIPv4or6,
    cerRpdAuxCoreDescription        DisplayString,
    cerRpdAuxCoreRowStatus          RowStatus
}

cerRpdAuxCoreRpdIndex OBJECT-TYPE
    SYNTAX CerRpdIndex
    MAX-ACCESS   not-accessible
    STATUS current
    DESCRIPTION
        "Index of the RPD using this Aux Core."
    ::= {cerRpdAuxCoreEntry 1}

cerRpdAuxCoreAddrType OBJECT-TYPE
    SYNTAX InetAddressType
    MAX-ACCESS   not-accessible
    STATUS current
    DESCRIPTION
        "Type of the AUX Core IP address; only IPv4 and IPv6 are allowed."
    ::= {cerRpdAuxCoreEntry 2}

cerRpdAuxCoreIpAddr OBJECT-TYPE
    SYNTAX InetAddressIPv4or6
    MAX-ACCESS not-accessible
    STATUS current
    DESCRIPTION
        "The IP address of this AUX core. Only length 4 for IPv4 and length 16 for
         IPv6 are allowed."
    ::= {cerRpdAuxCoreEntry 3}

cerRpdAuxCoreDescription OBJECT-TYPE
    SYNTAX       DisplayString (SIZE(0..32))
    MAX-ACCESS   read-create
    STATUS       current
    DESCRIPTION
        "The description of the AUX core."
    DEFVAL { "" }
    ::= {cerRpdAuxCoreEntry 4}

cerRpdAuxCoreRowStatus   OBJECT-TYPE
    SYNTAX      RowStatus
    MAX-ACCESS  read-create
    STATUS      current
    DESCRIPTION
        "The RowStatus for controlling entries in this table. 
         Allowed values are createAndGo, destroy, and active."
    ::= { cerRpdAuxCoreEntry 5 }
END
